FME workspace FME training 5 integration-presentation huiswerk.fmw
Title: Test

Parameters:
- DestDataset_MSSQL_AZURE = sql server   # Azure SQL Database Connection
- SourceDataset_MSSQL_AZURE = Microsoft Azure SQL server df   # Azure SQL Database Connection
- SourceDataset_MSSQL_AZURE_4 = Microsoft Azure SQL server df   # Azure SQL Database Connection
- SourceDataset_POSTGIS_3 = PostgreSQL   # Connection
- DestDataset_POSTGIS = PostgreSQL   # Connection

Readers:
- MSSQL_AZURE_3: MSSQL_AZURE from $(SourceDataset_MSSQL_AZURE)
- MSSQL_AZURE_2: MSSQL_AZURE from $(SourceDataset_MSSQL_AZURE_4)
- POSTGIS_2: POSTGIS from $(SourceDataset_POSTGIS_3)

Writers:
- MSSQL_AZURE_1: MSSQL_AZURE to $(DestDataset_MSSQL_AZURE)
- POSTGIS_1: POSTGIS to $(DestDataset_POSTGIS)

Junction_3
    -> TestFilter_2
    -> Tester_6

Bookmark: Reader Grenzen Limburg
oracle_cbs_grenzen_limburg (reader POSTGIS_2)
    attributes: bronsysteem varchar(6), creatie_datum varchar(200), valide varchar(2), aantal_huishoudens float8, aantal_inwoners float8, bevolkingsdichth_inwoners_km2 float8, buurtcode varchar(10), buurtnaam varchar(55), dekkingspercentage float8, gemeentecode varchar(6), gemeentenaam varchar(22), gemiddelde_huishoudsgrootte float8, indelingswijziging_wijk_buurt float8, jaarstatcode varchar(10), mannen float8, meest_voorkomende_postcode int4, omgevingsadressendichtheid float8, oppervlakte_land_in_ha float8, oppervlakte_totaal_in_ha float8, oppervlakte_water_in_ha float8, perc_huishoudens_met_kinderen float8, perc_huishoudens_zonder_kinder float8, perc_niet_westerse_migratieach float8, perc_overige_nietwestersemigra float8, perc_uit_ned_antillen_en_aruba float8, perc_westerse_migratieachtergr float8, percent_eenpersoonshuishoudens float8, percent_personen_0_tot_15_jr float8, percent_personen_15_tot_25_jr float8, percent_personen_25_tot_45_jr float8,
      percent_personen_45_tot_65_jr float8, percent_personen_65_j_en_ouder float8, percentage_gehuwd float8, percentage_gescheid float8, percentage_ongehuwd float8, percentage_uit_marokko float8, percentage_uit_suriname float8, percentage_uit_turkije float8, percentage_verweduwd float8, se_anno_cad_data varchar(200), stedelijkheid_adressen_per_km2 float8, vrouwen float8, water varchar(3), wijkcode varchar(8), wijknaam varchar(39), _issues{}_count int8, _issues{}_issue_found varchar, _issues{}_location_sample_x float8, _issues{}_location_sample_y float8, _issues{}_location_sample_z float8, _issues{}_repair_state varchar, locatie_id uuid
    -> AttributeKeeper

Bookmark: Grenzen Limburg: Regio's toevoegen aan dataset
AttributeKeeper
    CREATE_BULK_MODE_FEATURES = NO
    KEEP_ATTRS = buurtcode,buurtnaam,gemeentecode,gemeentenaam,wijkcode,wijknaam,locatie_id
    -> StringCaseChanger
StringCaseChanger
    ATTRCHOICE = SELECTED
    ATTRLIST = buurtnaam gemeentenaam wijknaam
    CHANGE_TYPE = lower
    -> TestFilter_3
Note: Bepaal de regio's
TestFilter_3
    DEFAULT_VALUE = zuid-limburg
    PASSED_TEST_GROUP_OUTPUT = FIRST
    TEST_LIST:
      "BOOL_OP,OR,COMPOSITE_TEST,""""""1 OR 2 OR 3 OR 4 OR 5 OR 6 OR 7"""""",TEST_CLAUSE,CASE_INSENSITIVE_TEST @Value(gemeentenaam) CONTAINS Bergen (L.)
      CASE_INSENSITIVE_TEST @Value(gemeentenaam) CONTAINS Gennep
      CASE_INSENSITIVE_TEST @Value(gemeentenaam) CONTAINS Horst aan de Maas
      CASE_INSENSITIVE_TEST @Value(gemeentenaam) CONTAINS Mook en Middelaar
      CASE_INSENSITIVE_TEST @Value(gemeentenaam) CONTAINS Peel en Maas
      CASE_INSENSITIVE_TEST @Value(gemeentenaam) CONTAINS Venlo
      CASE_INSENSITIVE_TEST @Value(gemeentenaam) CONTAINS Venray",noord-limburg,"BOOL_OP,OR,COMPOSITE_TEST,""""""1 OR 2 OR 3 OR 4 OR 5 OR 6 OR 7 OR 8"""""",TEST_CLAUSE,CASE_INSENSITIVE_TEST @Value(gemeentenaam) CONTAINS Beesel
      CASE_INSENSITIVE_TEST @Value(gemeentenaam) CONTAINS Echt-Susteren
      CASE_INSENSITIVE_TEST @Value(gemeentenaam) CONTAINS Leudal
      CASE_INSENSITIVE_TEST @Value(gemeentenaam) CONTAINS Maasgouw
      CASE_INSENSITIVE_TEST @Value(gemeentenaam) CONTAINS Nederweert
      CASE_INSENSITIVE_TEST @Value(gemeentenaam) CONTAINS Roerdalen
      CASE_INSENSITIVE_TEST @Value(gemeentenaam) CONTAINS Roermond
      CASE_INSENSITIVE_TEST @Value(gemeentenaam) CONTAINS Weert",midden-limburg,"BOOL_OP,OR,COMPOSITE_TEST,""""""1 OR 2 OR 3 OR 4 OR 5 OR 6 OR 7 OR 8 OR 9 OR 10 OR 11 OR 12 OR 13 OR 14 OR 15 OR 16"""""",TEST_CLAUSE,CASE_INSENSITIVE_TEST @Value(gemeentenaam) CONTAINS Beek
      CASE_INSENSITIVE_TEST @Value(gemeentenaam) CONTAINS Beekdaelen
      CASE_INSENSITIVE_TEST @Value(gemeentenaam) CONTAINS Brunssum
      CASE_INSENSITIVE_TEST @Value(gemeentenaam) CONTAINS Eijsden-Margraten
      CASE_INSENSITIVE_TEST @Value(gemeentenaam) CONTAINS Gulpen-Wittem
      CASE_INSENSITIVE_TEST @Value(gemeentenaam) CONTAINS Heerlen
      CASE_INSENSITIVE_TEST @Value(gemeentenaam) CONTAINS Kerkrade
      CASE_INSENSITIVE_TEST @Value(gemeentenaam) CONTAINS Landgraaf
      CASE_INSENSITIVE_TEST @Value(gemeentenaam) CONTAINS Maastricht
      CASE_INSENSITIVE_TEST @Value(gemeentenaam) CONTAINS Meerssen
      CASE_INSENSITIVE_TEST @Value(gemeentenaam) CONTAINS Simpelveld
      CASE_INSENSITIVE_TEST @Value(gemeentenaam) CONTAINS Sittard-Geleen
      CASE_INSENSITIVE_TEST @Value(gemeentenaam) CONTAINS Stein
      CASE_INSENSITIVE_TEST @Value(gemeentenaam) CONTAINS Vaals
      CASE_INSENSITIVE_TEST @Value(gemeentenaam) CONTAINS Valkenburg aan de Geul
      CASE_INSENSITIVE_TEST @Value(gemeentenaam) CONTAINS Voerendaal",zuid-limburg
    noord-limburg -> AttributeCreator
    midden-limburg -> AttributeCreator_2
    zuid-limburg -> AttributeCreator_3
AttributeCreator
    ATTR_TABLE = SET_TO regio (varchar(13)) = noord-limburg
    -> Junction_5
AttributeCreator_2
    ATTR_TABLE = SET_TO regio (varchar(14)) = midden-limburg
    -> Junction_5
AttributeCreator_3
    ATTR_TABLE = SET_TO regio (varchar(12)) = zuid-limburg
    -> Junction_5
Junction_5
    -> FeatureMerger_2 [SUPPLIER]
    -> FM_gemeentenaam [SUPPLIER]
    -> StringReplacer

Bookmark: Pas wijknaam aan
Note: dim_locatie
StringReplacer
    CASE = NO
    FIND_TEXT = ^Wijk *\d\d:*
    NO_MATCH = _FME_NO_OP_
    REGEXP = YES
    SRC_ATTRS = wijknaam
    TEST_STRING = Wijk 00 SSchas
    -> AttributeTrimmer_2
AttributeTrimmer_2
    SRC_ATTRS = wijknaam
    TRIM_TO_NONE = Yes
    TRIM_TYPE = BOTH
    -> Tester_4
    -> dim_locatie (writer POSTGIS_1)
dim_locatie (writer POSTGIS_1)
    attributes: locatie_id uuid,PrimaryKey, regio varchar(15), buurtcode varchar(10), buurtnaam varchar(55), gemeentecode varchar(6), gemeentenaam varchar(22), wijkcode varchar(8), wijknaam varchar(39)

Bookmark: Koppel locatie_id aan het Antwoord veld aan buurtnaam/gemeentenaam/wijknaam
Tester_4
    BOOL_OP = OR
    TEST_CLAUSE = TEST @StringLength(@Value(wijknaam)) > 1
    TEST_MODE = TEST
    PASSED -> FeatureMerger_3 [SUPPLIER]
Note: Gemeentenaam
FM_gemeentenaam: FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(antwoord) @Value(gemeentenaam) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> Junction_2
    UNMERGED_REQUESTOR -> FeatureMerger_2 [REQUESTOR]
Note: Buurtnaam
FeatureMerger_2
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(antwoord) @Value(buurtnaam) AUTO
    MERGE_TYPE_VAL = GEOM_AND_ATTRS
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes and Geometry
    MERGED -> Junction_2
    UNMERGED_REQUESTOR -> FeatureMerger_3 [REQUESTOR]
Note: Wijknaam
FeatureMerger_3
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(antwoord) @Value(wijknaam) AUTO
    MERGE_TYPE_VAL = GEOM_AND_ATTRS
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes and Geometry
    MERGED -> Junction_2
Junction_2
    -> Aggregator
Aggregator
    ACCUM_ATTRS = None
    AGGREGATE_TYPE = Homogeneous Collection (If Possible)
    CONCAT_ATTRS = antwoord
    GROUP_BY = aanvraagnummer
    LIST_ATTRS_TO_INCLUDE = locatie_id
    LIST_NAME = locatie_id
    MODE = Geometry - Assemble One Level
    SEP = ,
    AGGREGATE -> ListExploder
ListExploder
    ATTR_CONFLICT_RES_LOOKUP = INCOMING_IF_CONFLICT
    INDEX_ATTR = _element_index
    LIST_ATTR = locatie_id{}
    ATTR_ACCUM_MODE = Merge List Attributes
    ATTR_CONFLICT_RES = Use List Attribute Values
    ELEMENTS -> Tester_3
Tester_3
    BOOL_OP = OR
    TEST_CLAUSE = TEST @Value(_element_index) = 0
    TEST_MODE = TEST
    PASSED -> StringReplacer_2
StringReplacer_2
    CASE = NO
    FIND_TEXT = \,.*$
    NO_MATCH = _FME_NO_OP_
    REGEXP = YES
    SRC_ATTRS = antwoord
    -> AttributeKeeper_3
Note: aanvraagnummers met locatie_id
AttributeKeeper_3
    CREATE_BULK_MODE_FEATURES = NO
    KEEP_ATTRS = aanvraagnummer,locatie_id
    -> FeatureJoiner_2 [RIGHT]

Bookmark: Reader Workflowformulieren
workflowformulieren_v1 (reader MSSQL_AZURE_3)
    attributes: aanvraagnummer varchar(9), antwoord varchar(8000), datum date, formulier varchar(56), hoofdfase varchar(15), regeling varchar(184), sharepoint_nummer varchar(12), vergadering_dossier_nummer varchar(200), vraag varchar(706), uniek_id char(26)
    -> Junction_3

Bookmark: Aantal bezoekers en vrijwilligers
Note: Aantal vrijwilligers / Aantal bezoekers
TestFilter_2
    DEFAULT_VALUE = <UNFILTERED>
    PASSED_TEST_GROUP_OUTPUT = FIRST
    TEST_LIST:
      "BOOL_OP,COMPOSITE,COMPOSITE_TEST,""""""1 OR 2 OR 3 OR 4 OR 5 OR 6 OR 7 AND 8"""""",TEST_CLAUSE,CASE_INSENSITIVE_TEST @Value(vraag) CONTAINS personen
      CASE_INSENSITIVE_TEST @Value(vraag) CONTAINS toeschouwers
      CASE_INSENSITIVE_TEST @Value(vraag) CONTAINS deelnemers
      CASE_INSENSITIVE_TEST @Value(vraag) CONTAINS leden
      CASE_INSENSITIVE_TEST @Value(vraag) CONTAINS doelgroep
      CASE_INSENSITIVE_TEST @Value(vraag) CONTAINS bezoekers
      CASE_INSENSITIVE_TEST @Value(vraag) CONTAINS publiek
      CASE_INSENSITIVE_TEST @Value(antwoord) TYPE NUM",Aantal bezoekers,"BOOL_OP,AND,COMPOSITE_TEST,""""""1 AND 2"""""",TEST_CLAUSE,CASE_INSENSITIVE_TEST @Value(vraag) CONTAINS vrijwilligers
      TEST @Value(antwoord) TYPE NUM",Aantal vrijwilligers
    Aantal bezoekers -> AttributeCreator_4
    Aantal vrijwilligers -> AttributeCreator_5
AttributeCreator_4
    ATTR_TABLE = SET_TO aantal_bezoekers (int32) = @Value(antwoord)
    -> Junction
AttributeCreator_5
    ATTR_TABLE = SET_TO aantal_vrijwilligers (int32) = @Value(antwoord)
    -> Junction
Junction
    -> AttributeKeeper_5
AttributeKeeper_5
    CREATE_BULK_MODE_FEATURES = NO
    KEEP_ATTRS = aantal_bezoekers,aantal_vrijwilligers,aanvraagnummer
    -> Aggregator_2
Aggregator_2
    ACCUM_ATTRS = None
    AGGREGATE_TYPE = Homogeneous Collection (If Possible)
    GROUP_BY = aanvraagnummer
    MODE = Geometry - Assemble One Level
    SEP = ,
    SUM = aantal_bezoekers aantal_vrijwilligers
    AGGREGATE -> FeatureJoiner [RIGHT]

Bookmark: Rijen met een locatie naar boven halen
Note: Filter de vragen en antwoorden met locatie erin
Tester_6
    BOOL_OP = AND
    TEST_CLAUSE:
      TEST antwoord ATTRIBUTE_HAS_A_VALUE ""
      CASE_SENSITIVE_TEST @Value(vraag) CONTAINS_REGEX (?i)(locatie<pipe>plaats<pipe>gemeente)
      CASE_SENSITIVE_TEST @Value(antwoord) NOT_CONTAINS_REGEX ^(Ja<pipe>Nee)$
      CASE_INSENSITIVE_TEST @Value(antwoord) NOT_CONTAINS n.v.t
      CASE_INSENSITIVE_TEST @Value(antwoord) NOT_CONTAINS nvt
    TEST_MODE = PER_TEST
    PASSED -> Tester_7
Note: Regio
Tester_7
    BOOL_OP = OR
    TEST_CLAUSE:
      CASE_INSENSITIVE_TEST @Value(antwoord) = Zuid-Limburg
      CASE_INSENSITIVE_TEST @Value(antwoord) = Midden-Limburg
      CASE_INSENSITIVE_TEST @Value(antwoord) = Noord-Limburg
    TEST_MODE = CASE_INSENSITIVE_TEST
    FAILED -> AttributeKeeper_7
AttributeKeeper_7
    CREATE_BULK_MODE_FEATURES = NO
    KEEP_ATTRS = aanvraagnummer,antwoord
    -> AttributeTrimmer
AttributeTrimmer
    SRC_ATTRS = antwoord
    TRIM_TO_NONE = Yes
    TRIM_TYPE = BOTH
    -> StringCaseChanger_2
StringCaseChanger_2
    ATTRCHOICE = SELECTED
    ATTRLIST = antwoord
    CHANGE_TYPE = lower
    -> FM_gemeentenaam [REQUESTOR]

Bookmark: Reader Aanvragen
aanvragen_v1 (reader MSSQL_AZURE_2)
    attributes: Privacy varchar(200), aangevraagd_bedrag bigint, vastgesteld_bedrag bigint, verleend_bedrag_of_bedrag_na_herziening_tussentijds bigint, aan_zet varchar(179), aangevraagd_via varchar(12), aanvraag_id varchar(24), aanvraagdatum datetime, aanvraagdatum_jaar integer, aanvraagdatum_maand tinyint, aanvraagdatum_weeknummer tinyint, aanvraagnummer varchar(9), aanvraagwijze_particulier_/_organisatie varchar(11), aanvrager_id varchar(24), aanvrager_naam varchar(14), actiestatus_medewerkers varchar(14), actieve__actie_11 varchar(79), actieve_actie_1 varchar(79), actieve_actie_2 varchar(79), actieve_actie_3 varchar(79), actieve_actie_4 varchar(79), actieve_actie_5 varchar(79), actieve_actie_6 varchar(60), actieve_actie_7 varchar(79), actieve_actie_8 varchar(60), actieve_actie_9 varchar(79), actieve_actie_10 varchar(60), actieve_actie_12 varchar(79), actieve_actie_13 varchar(60), actieve_actie_14 varchar(60),
      actieve_actie_15 varchar(60), actieve_actie_16 varchar(32), actieve_actie_17 varchar(34), actieve_actie_18 varchar(16), actieve_actie_19 varchar(17), actieve_actie_20 varchar(26), actieve_actie_21 varchar(14), actieve_actie_22 varchar(14), actieve_actie_23 varchar(33), actieve_actie_24 varchar(14), actieve_actie_25 varchar(33), actieve_actie_26 varchar(33), actieve_actie_27 varchar(50), actieve_actie_28 varchar(50), actieve_actie_29 varchar(50), actieve_actie_30 varchar(50), actieve_actie_31 varchar(24), actuele_actieve_hoofdfase varchar(15), actuele_actieve_subfase varchar(21), actuele_status varchar(29), afdeling_hoofdgroep varchar(12), besluit_genomen_1_verlening varchar(3), besluit_genomen_2_steekproef varchar(3), besluit_genomen_3_melding varchar(3), besluit_genomen_4_vaststelling varchar(3), besluit_genomen_correcties varchar(3), besluit_genomen_correcties_fb varchar(3), besluit_genomen_overige varchar(3), besluitvorming varchar(19), betaald varchar(13),
      boekjaar varchar(24), datum_besluit_1_verlening varchar(10), datum_besluit_2_steekproef varchar(10), datum_besluit_3_melding varchar(10), datum_besluit_4_vaststelling varchar(10), datum_besluit_correcties varchar(200), datum_besluit_correcties_fb varchar(200), datum_besluit_jaar_1_verlening integer, datum_besluit_jaar_2_steekproef integer, datum_besluit_jaar_3_melding integer, datum_besluit_jaar_4_vaststelling integer, datum_besluit_jaar_correcties varchar(200), datum_besluit_jaar_correcties_fb varchar(200), datum_besluit_jaar_overige varchar(200), datum_besluit_maand_1_verlening tinyint, datum_besluit_maand_2_steekproef tinyint, datum_besluit_maand_3_melding tinyint, datum_besluit_maand_4_vaststelling tinyint, datum_besluit_maand_correcties varchar(200), datum_besluit_maand_correcties_fb varchar(200), datum_besluit_maand_overige varchar(200), datum_besluit_overige varchar(200), datum_besluit_weeknummer_1_verlening tinyint, datum_besluit_weeknummer_2_steekproef tinyint, datum_besluit_weeknummer_3_melding tinyint, datum_besluit_weeknummer_4_vaststelling tinyint, datum_besluit_weeknummer_correcties varchar(200), datum_besluit_weeknummer_correcties_fb varchar(200), datum_besluit_weeknummer_overige varchar(200), deadline_hoofdfase varchar(10),
      documentnummer_besluit_1_verlening varchar(13), documentnummer_besluit_2_steekproef varchar(13), documentnummer_besluit_3_melding varchar(13), documentnummer_besluit_4_vaststelling varchar(13), documentnummer_besluit_correcties varchar(200), documentnummer_besluit_correcties_fb varchar(200), documentnummer_besluit_overige varchar(200), doorlooptijd:_912_juridisch_advies tinyint, doorlooptijd:_913_inhoudelijk_advies tinyint, doorlooptijd:_declaratie_indienen integer, doorlooptijd:_eindverantwoording_automatisch_opvragen tinyint, doorlooptijd:_iban_wijzigen tinyint, doorlooptijd:_intrekken_aanvraag tinyint, doorlooptijd:_melding_doorgeven integer, doorlooptijd:_tussenverantwoording_automatisch_opvragen tinyint, doorlooptijd:_vraag_stellen_/_bericht_sturen tinyint, einddatum_activiteiten datetime, einddatum_taak datetime, einddatum_termijnbewaking datetime, einddatum_termijnbewaking_1_verlening varchar(10), einddatum_termijnbewaking_2_steekproef varchar(10), einddatum_termijnbewaking_3_melding varchar(10), einddatum_termijnbewaking_4_vaststelling varchar(10), einddatum_termijnbewaking_correcties varchar(200), einddatum_termijnbewaking_correcties_fb varchar(200), einddatum_termijnbewaking_overige varchar(200), einddatum_termijnbewaking_resterende_dagen_1_verlening varchar(20), einddatum_termijnbewaking_resterende_dagen_2_steekproef varchar(20), einddatum_termijnbewaking_resterende_dagen_3_melding varchar(20), einddatum_termijnbewaking_resterende_dagen_4_vaststelling varchar(20),
      einddatum_termijnbewaking_resterende_dagen_correcties varchar(200), einddatum_termijnbewaking_resterende_dagen_correcties_fb varchar(200), einddatum_termijnbewaking_resterende_dagen_overige varchar(200), einddatum_termijnbewaking_resterende_weken_1_verlening varchar(20), einddatum_termijnbewaking_resterende_weken_2_steekproef varchar(20), einddatum_termijnbewaking_resterende_weken_3_melding varchar(20), einddatum_termijnbewaking_resterende_weken_4_vaststelling varchar(20), einddatum_termijnbewaking_resterende_weken_correcties varchar(200), einddatum_termijnbewaking_resterende_weken_correcties_fb varchar(200), einddatum_termijnbewaking_resterende_weken_overige varchar(200), functioneel_beheer varchar(26), functioneel_beheer_groep varchar(19), gebruiker_1 varchar(27), gebruiker_2 varchar(27), gebruiker_3 varchar(27), gebruiker_4 varchar(27), gebruiker_5 varchar(27), gebruiker_6 varchar(27), gebruiker_7 varchar(27), gebruiker_8 varchar(27), gebruiker_9 varchar(27), gebruiker_10 varchar(27), gebruiker_11 varchar(27), gebruiker_12 varchar(27), gebruiker_13 varchar(27), gebruiker_14 varchar(27), gebruiker_15 varchar(27), gebruiker_16 varchar(27), gebruiker_17 varchar(27), gebruiker_18 varchar(27),
      gebruiker_19 varchar(27), gebruiker_20 varchar(27), gebruiker_21 varchar(27), gebruiker_22 varchar(27), gebruiker_23 varchar(27), gebruiker_24 varchar(27), gebruiker_25 varchar(27), gebruiker_26 varchar(27), gebruiker_27 varchar(17), gebruiker_28 varchar(17), gebruiker_29 varchar(17), gebruiker_30 varchar(17), gebruiker_31 varchar(12), gebruikersrol_1 varchar(17), gebruikersrol_2 varchar(17), gebruikersrol_3 varchar(17), gebruikersrol_4 varchar(17), gebruikersrol_5 varchar(17), gebruikersrol_6 varchar(17), gebruikersrol_7 varchar(17), gebruikersrol_8 varchar(17), gebruikersrol_9 varchar(17), gebruikersrol_10 varchar(17), gebruikersrol_11 varchar(17), gebruikersrol_12 varchar(17), gebruikersrol_13 varchar(17), gebruikersrol_14 varchar(17), gebruikersrol_15 varchar(17), gebruikersrol_16 varchar(11), gebruikersrol_17 varchar(17),
      gebruikersrol_18 varchar(8), gebruikersrol_19 varchar(8), gebruikersrol_20 varchar(8), gebruikersrol_21 varchar(8), gebruikersrol_22 varchar(8), gebruikersrol_23 varchar(8), gebruikersrol_24 varchar(8), gebruikersrol_25 varchar(8), gebruikersrol_26 varchar(8), gebruikersrol_27 varchar(17), gebruikersrol_28 varchar(17), gebruikersrol_29 varchar(17), gebruikersrol_30 varchar(17), gebruikersrol_31 varchar(11), gegenereerd_veld_handmatig_ingevuld varchar(3), gemachtigde varchar(200), gemachtigde_id varchar(200), huidig_definitief_besluit varchar(26), opschorting_1 integer, opschorting_2 integer, opschorting_3 tinyint, opschorting_4 tinyint, opschorting_fase_1 varchar(15), opschorting_fase_2 varchar(15), opschorting_fase_3 varchar(15), opschorting_fase_4 varchar(12), organisatie_id varchar(24), organisatie_naam varchar(186), periodiciteit_activiteiten varchar(18), portefeuillehouder_monitoring varchar(22),
      portefeuillehouder_vaststelling varchar(28), portefeuillehouder_verlening varchar(102), project_assistent varchar(65), project_assistent_groep varchar(19), regeling_id varchar(24), regelingnaam varchar(184), regelingnummer tinyint, rvo_dossiernummer bigint, saldo varchar(13), sas-conversiedossier varchar(2), sas-dossiernummer varchar(14), sas-regeling varchar(107), sharepoint_nummer varchar(12), startdatum_activiteiten varchar(10), startdatum_termijnbewaking_1_verlening varchar(10), startdatum_termijnbewaking_2_steekproef varchar(10), startdatum_termijnbewaking_3_melding varchar(10), startdatum_termijnbewaking_4_vaststelling varchar(10), startdatum_termijnbewaking_correcties varchar(200), startdatum_termijnbewaking_correcties_fb varchar(200), startdatum_termijnbewaking_overige varchar(200), status_termijnbewaking_1_verlening varchar(26), status_termijnbewaking_2_steekproef varchar(26), status_termijnbewaking_3_melding varchar(26), status_termijnbewaking_4_vaststelling varchar(26), status_termijnbewaking_correcties varchar(200), status_termijnbewaking_correcties_fb varchar(200), status_termijnbewaking_overige varchar(200), statuskleur_termijnbewaking_actieve_hoofdfase varchar(6), stemlijst_besluit varchar(200),
      stemlijst_resultaat varchar(200), subsidietype varchar(18), team_subgroep varchar(19), termijnbewaking_verdaagd_1_verlening varchar(3), termijnbewaking_verdaagd_2_steekproef varchar(3), termijnbewaking_verdaagd_3_melding varchar(3), termijnbewaking_verdaagd_4_vaststelling varchar(3), termijnbewaking_verdaagd_correcties varchar(200), termijnbewaking_verdaagd_correcties_fb varchar(200), termijnbewaking_verdaagd_overige varchar(200), titel_aanvraag varchar(246), vaststeller varchar(47), vaststeller_groep varchar(19), vergadering_besluit varchar(200), vergadering_dossier_nummer varchar(200), verlener varchar(64), verlener_-_groep varchar(40), vrijval varchar(200)
    -> AttributeKeeper_4

Bookmark: fact_subidieaanvraag
AttributeKeeper_4
    CREATE_BULK_MODE_FEATURES = NO
    KEEP_ATTRS = aangevraagd_bedrag,aanvraagdatum,aanvraagnummer,vastgesteld_bedrag,verleend_bedrag_of_bedrag_na_herziening_tussentijds,aanvraag_id,aanvrager_id,regeling_id
    -> AttributeRenamer_2
AttributeRenamer_2
    ATTR_TABLE = RENAME_SET_DEFAULT verleend_bedrag_of_bedrag_na_herziening_tussentijds > verleend_bedrag
    KEEP_RENAMED_ONLY = no
    MISSING_INPUT_ATTRS = REMOVE
    -> FeatureJoiner [LEFT]
Note: Vrijilligers / BEzoekers
FeatureJoiner
    ATTR_CONFLICT_RES_LOOKUP = USE_LEFT
    GEOMETRY_HANDLING_LOOKUP = USE_LEFT
    JOIN_KEYS = aanvraagnummer aanvraagnummer AUTO
    JOIN_MODE = Left
    ATTR_CONFLICT_RES = Prefer Left
    GEOMETRY_HANDLING = Prefer Left
    JOINED -> FeatureJoiner_2 [LEFT]
Note: locatie_id
FeatureJoiner_2
    ATTR_CONFLICT_RES_LOOKUP = USE_LEFT
    GEOMETRY_HANDLING_LOOKUP = USE_LEFT
    JOIN_KEYS = aanvraagnummer aanvraagnummer AUTO
    JOIN_MODE = Left
    ATTR_CONFLICT_RES = Prefer Left
    GEOMETRY_HANDLING = Prefer Left
