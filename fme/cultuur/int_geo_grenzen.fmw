FME workspace int_geo_grenzen.fmw

Parameters:
- bronsysteem = oracle
- DestDataset_POSTGIS = PostgreSQL   # Connection

Writers:
- POSTGIS_1: POSTGIS to $(DestDataset_POSTGIS)

oracle_cbs_grenzen_limburg_dk (writer POSTGIS_1)
    attributes: bronsysteem varchar(200), creatiedatum timestamp, valide varchar(2), aantal_huishoudens int4, aantal_inwoners int4, bevolkingsdichth_inwoners_km2 int4, buurtcode varchar(10), buurtnaam varchar(55), dekkingspercentage int4, gemeentecode varchar(6), gemeentenaam varchar(22), gemiddelde_huishoudsgrootte float8, indelingswijziging_wijk_buurt int2, jaarstatcode varchar(10), mannen int4, meest_voorkomende_postcode int4, omgevingsadressendichtheid int4, oppervlakte_land_in_ha int4, oppervlakte_totaal_in_ha int4, oppervlakte_water_in_ha int4, parquet_schema_name varchar(11), parquet_type varchar(12), perc_huishoudens_met_kinderen int4, perc_huishoudens_zonder_kinder int4, perc_niet_westerse_migratieach int4, perc_overige_nietwestersemigra int4, perc_uit_ned_antillen_en_aruba int4, perc_westerse_migratieachtergr int4, percent_eenpersoonshuishoudens int4, percent_personen_0_tot_15_jr int4,
      percent_personen_15_tot_25_jr int4, percent_personen_25_tot_45_jr int4, percent_personen_45_tot_65_jr int4, percent_personen_65_j_en_ouder int4, percentage_gehuwd int4, percentage_gescheid int4, percentage_ongehuwd int4, percentage_uit_marokko int4, percentage_uit_suriname int4, percentage_uit_turkije int4, percentage_verweduwd int4, se_anno_cad_data varchar(200), stedelijkheid_adressen_per_km2 int4, vrouwen int4, water varchar(3), wijkcode varchar(8), wijknaam varchar(39), _issues{}_count int8, _issues{}_issue_found varchar, _issues{}_location_sample_x float8, _issues{}_location_sample_y float8, _issues{}_location_sample_z float8, _issues{}_repair_state varchar, locatie_id char(16)

Bookmark: Web connectie - load data
Creator_2
    GEOMTYPE = Geometry Object
    NUM = 1
    CREATED -> AzureBlobStorageConnector_2
AzureBlobStorageConnector_2
    CREDENTIAL_SOURCE = WEBCONN
    OPERATION_TYPE = List
    PARAMETER_SETUP = _FME_AZURE_CONTAINER][{"display":"raw","value":"raw"}]]_FME_FILES][{"display":"/geodatabasePGIS","value":"geodatabasePGIS/"}]]_FME_INCLUDE_SUBFOLDERS]No]_FME_ATTRIBUTES_TO_ADD]"_url _full_path _name _created"]FME_CONTROLLER_QUERY_FILE]]FME_CONTROLLER_CHOICE]List
    _FME_AZURE_CONNECTION = Blobstorage
    -> FeatureReader_2 [INITIATOR]

Bookmark: Load attributes
FeatureReader_2
    ATTR_ACCUM_MODE = Only Use Result
    CLIP_TO_ENVELOPE = NO
    COMBINE_GEOM = Use Result
    DATASET = @Value(_url)
    FORMAT = GEOPARQUET
    GEOPARQUET_SUPPORT_ANNOTATED_LISTS = yes
    GEOPARQUET_SUPPORT_LISTS = yes
    GEOPARQUET_SUPPORT_LOCAL_TIME = yes
    INITIATOR_FIRST_OUTPUT = default
    INTERACT = NONE
    ORDER_RESULTS = No
    OUTPUT_ADD_SCHEMA_ATTRIBUTES = NO
    OUTPUT_FEATURES_DISPLAY = Schema and Data Features
    <OTHER> -> AttributeExposer_2
AttributeExposer_2
    ATTR_TABLE = AANTAL_HUISHOUDENS,uint16,AANTAL_INWONERS,uint16,BEVOLKINGSDICHTH_INWONERS_KM2,int32,BUURTCODE,varchar(10),BUURTNAAM,varchar(55),DEKKINGSPERCENTAGE,int32,GEMEENTECODE,varchar(6),GEMEENTENAAM,varchar(22),GEMIDDELDE_HUISHOUDSGROOTTE,real64,INDELINGSWIJZIGING_WIJK_BUURT,uint8,JAARSTATCODE,varchar(10),MANNEN,uint16,MEEST_VOORKOMENDE_POSTCODE,int32,OMGEVINGSADRESSENDICHTHEID,int32,OPPERVLAKTE_LAND_IN_HA,uint16,OPPERVLAKTE_TOTAAL_IN_HA,uint16,OPPERVLAKTE_WATER_IN_HA,uint16,parquet_schema_name,varchar(11),parquet_type,varchar(12),PERC_HUISHOUDENS_MET_KINDEREN,int32,PERC_HUISHOUDENS_ZONDER_KINDER,int32,PERC_NIET_WESTERSE_MIGRATIEACH,int32,PERC_OVERIGE_NIETWESTERSEMIGRA,int32,PERC_UIT_NED_ANTILLEN_EN_ARUBA,int32,PERC_WESTERSE_MIGRATIEACHTERGR,int32,PERCENT_EENPERSOONSHUISHOUDENS,int32,PERCENT_PERSONEN_0_TOT_15_JR,int32,PERCENT_PERSONEN_15_TOT_25_JR,int32,PERCENT_PERSONEN_25_TOT_45_JR,int32,PERCENT_PERSONEN_45_TOT_65_JR,int32,PERCENT_PERSONEN_65_J_EN_OUDER,int32,PERCENTAGE_GEHUWD,int32,PERCENTAGE_GESCHEID,int32,PERCENTAGE_ONGEHUWD,int32,PERCENTAGE_UIT_MAROKKO,int32,PERCENTAGE_UIT_SURINAME,int32,PERCENTAGE_UIT_TURKIJE,int32,PERCENTAGE_VERWEDUWD,int32,SE_ANNO_CAD_DATA,varchar(200),STEDELIJKHEID_ADRESSEN_PER_KM2,int32,VROUWEN,uint16,WATER,varchar(3),WIJKCODE,varchar(8),WIJKNAAM,varchar(39),WKT_SHAPE,varchar(306358)
    -> GeometryReplacer

Bookmark: Geometry
GeometryReplacer
    KIND = wkt
    OGC_WKT_PRECISION = FLOAT_64
    REMOVE_ATTRIBUTE = Yes
    SOURCE = @Value(WKT_SHAPE)
    KIND_LONG = OGC Well Known Text
    OGC_WKT_PRECISION_DISPLAY = 64-bit
    -> CoordinateSystemSetter
CoordinateSystemSetter
    COORDSYS = EPSG:28992
    -> GeometryValidator
GeometryValidator
    ISSUE_ATTR_NAME = _issues
    PRESETS = Custom
    REPAIR = Yes
    RULES = OGC_VALID_CHECK OGC_VERSION]V1.2.0]FME_CONTROLLER_QUERY_FILE]]FME_CONTROLLER_CHOICE]OGC_VALID_CHECK
    SUMMARY = Detailed
    PASSED -> AC_valid
    FAILED -> AC_invalid
AC_valid: AttributeCreator
    ATTR_TABLE = SET_TO Valide (varchar(2)) = Ja
    -> Junction
AC_invalid: AttributeCreator
    ATTR_TABLE = SET_TO Valide (varchar(23)) = _issues{0}.issue_found​
    -> Junction
Junction
    -> AC_bron_creatiedatum
AC_bron_creatiedatum: AttributeCreator
    ATTR_TABLE:
      SET_TO Bronsysteem (varchar(200)) = $(bronsysteem)
      SET_TO Creatiedatum (datetime) = @DateTimeNow()
    -> CRCCalculator
CRCCalculator
    ALG_TYPE = MD5
    CALC_ATTRS = BUURTCODE GEMEENTECODE WIJKCODE
    CRC_ATTR = locatie_id
    CRC_TYPE = ATTRIBUTES_ENCODED
    ALG_CHOICES = MD5
    -> oracle_cbs_grenzen_limburg_dk (writer POSTGIS_1)
