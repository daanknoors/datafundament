FME workspace int_susy_workflowformulieren.fmw

Parameters:
- _meta_privacy = geen_persoonsgegevens   # privacy
- _Azure_Container = raw   # Container input bestand(en)
- _Azure_Folder = staging/Susy/   # Pad naar input bestand(en) in Azure
- DestDataset_MSSQL_AZURE_6 = Microsoft Azure SQL server df   # Azure SQL Database Connection

Writers:
- MSSQL_AZURE_3: MSSQL_AZURE to $(DestDataset_MSSQL_AZURE_6)

Bookmark: Workflow formulieren
Load_csv_file_workflow: load_csv_from_blob
    _FME_AZURE_CONTAINER = $(_Azure_Container)
    _FME_Azure_Folder = $(_Azure_Folder)
    _Filename = arrangementWorkflowForm.csv
    Load_CSV_Output -> AttributeExposer_2
AttributeExposer_2
    ATTR_TABLE = Aanvraagnummer,varchar(433),Antwoord,varchar(14134),csv_line_number,uint32,csv_number_of_fields,uint8,csv_total_number_of_columns,uint8,csv_type,varchar(8),Datum,varchar(10),Formulier,varchar(56),Hoofdfase,varchar(15),Regeling,varchar(184),"SharePoint nummer",varchar(315),"Vergadering dossier nummer",varchar(324),Vraag,varchar(708)
    -> Clean_column_names_2 [lowercase_attributes_Input]
Clean_column_names_2: clean_column_names
    only_retain_letters_number_underscores_Output -> CRCCalculator_2

Bookmark: Add hash identifier and remove duplicates
CRCCalculator_2
    ALG_TYPE = MD5
    CRC_ATTR = hash_key
    CRC_TYPE = ALL_ATTRS_ENCODED
    ALG_CHOICES = MD5
    -> DuplicateFilter
DuplicateFilter
    INPUT_ORDERED_CHOICE_LOOKUP = NO
    KEYATTR = hash_key
    INPUT_ORDERED_CHOICE = No
    UNIQUE -> DateTimeConverter_5

Bookmark: Convert date column
DateTimeConverter_5
    DATETIME_ATTR = datum
    IN_FORMAT = %d-%m-%Y$
    OUT_FORMAT = %Y-%m-%d
    PASSTHROUGH = YES
    REPAIR_INPUT = YES
    -> AttributeManager_4
AttributeManager_4
    -> workflowformulieren (writer MSSQL_AZURE_3)

Bookmark: Wegschrijven
workflowformulieren (writer MSSQL_AZURE_3)
    attributes: aanvraagnummer varchar(433), antwoord varchar(14134), datum date, formulier varchar(56), hoofdfase varchar(15), regeling varchar(184), sharepoint_nummer varchar(315), vergadering_dossier_nummer varchar(324), vraag varchar(708), hash_key char(16),PrimaryKey
