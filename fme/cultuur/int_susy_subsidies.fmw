FME workspace int_susy_subsidies.fmw

Parameters:
- _meta_privacy = geen_persoonsgegevens   # privacy
- _Azure_Container = raw   # Container input bestand(en)
- _Azure_Folder = staging/Susy/   # Pad naar input bestand(en) in Azure
- DestDataset_MSSQL_AZURE_7 = Microsoft Azure SQL server df   # Azure SQL Database Connection
- DestDataset_MSSQL_AZURE_5 = Microsoft Azure SQL server df   # Azure SQL Database Connection

Writers:
- MSSQL_AZURE_2: MSSQL_AZURE to $(DestDataset_MSSQL_AZURE_7)
- MSSQL_AZURE_4: MSSQL_AZURE to $(DestDataset_MSSQL_AZURE_5)

budgetassign (writer MSSQL_AZURE_4)
    attributes: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

Bookmark: Subsidies
Load_csv_file_project: load_csv_from_blob
    _FME_AZURE_CONTAINER = $(_Azure_Container)
    _FME_Azure_Folder = $(_Azure_Folder)
    _Filename = project.csv
    Load_CSV_Output -> AttributeExposer
AttributeExposer
    ATTR_TABLE = "Aan zet",varchar(183),"Aangevraagd bedrag",varchar(22),"Aangevraagd via",varchar(19),"Aanvraag ID",varchar(24),Aanvraagdatum,varchar(17),Aanvraagdatum00,varchar(19),"Aanvraagdatum (jaar)",varchar(10),"Aanvraagdatum (maand)",uint16,"Aanvraagdatum (weeknummer)",varchar(3),Aanvraagnummer,varchar(9),"Aanvraagwijze (Particulier / Organisatie)",varchar(15),"Aanvrager ID",varchar(24),"Aanvrager naam",varchar(88),"Actiestatus medewerkers",varchar(15),"Actieve actie 1",varchar(79),"Actieve actie 2",varchar(79),"Actieve actie 3",varchar(60),"Actieve actie 4",varchar(79),"Actieve actie 5",varchar(79),"Actieve actie 6",varchar(60),"Actieve actie 7",varchar(79),"Actieve actie 8",varchar(60),"Actieve actie 9",varchar(60),"Actieve actie 10",varchar(79),"Actieve actie 11",varchar(79),"Actieve actie 12",varchar(79),"Actieve actie 13",varchar(60),"Actieve actie 14",varchar(60),"Actieve actie 15",varchar(60),"Actieve actie 16",varchar(57),"Actieve actie 17",varchar(57),"Actieve actie 18",varchar(57),"Actieve actie 19",varchar(38),"Actieve actie 20",varchar(38),"Actieve actie 21",varchar(38),"Actieve actie 22",varchar(38),"Actieve actie 23",varchar(38),"Actieve actie 24",varchar(38),"Actieve actie 25",varchar(38),"Actieve actie 26",varchar(38),"Actieve actie 27",varchar(50),"Actieve actie 28",varchar(50),"Actieve actie 29",varchar(50),"Actieve actie 30",varchar(50),"Actieve actie 31",varchar(38),"Actieve actie 32",varchar(38),"Actieve actie 33",varchar(38),"Actieve actie 34",varchar(38),"Actieve actie 35",varchar(38),"Actieve actie 36",varchar(38),"Actieve actie 37",varchar(38),"Actieve actie 38",varchar(38),"Actieve actie 39",varchar(38),"Actieve actie 40",varchar(38),"Actieve actie 41",varchar(38),"Actieve actie 42",varchar(38),"Actieve actie 43",varchar(38),"Actieve actie 44",varchar(38),"Actieve actie 45",varchar(38),"Actieve actie 46",varchar(38),"Actieve actie 47",varchar(38),"Actieve actie 48",varchar(38),"Actieve actie 49",varchar(38),"Actieve actie 50",varchar(38),"Actieve actie 51",varchar(38),"Actieve actie 52",varchar(38),"Actieve actie 53",varchar(38),"Actieve actie 54",varchar(38),"Actieve actie 55",varchar(38),"Actieve actie 56",varchar(38),"Actieve actie 57",varchar(38),"Actieve actie 58",varchar(38),"Actieve actie 59",varchar(38),"Actieve actie 60",varchar(38),"Actieve actie 61",varchar(38),"Actieve actie 62",varchar(38),"Actieve actie 63",varchar(38),"Actieve actie 64",varchar(38),"Actieve actie 65",varchar(38),"Actieve actie 66",varchar(38),"Actieve actie 67",varchar(38),"Actieve actie 68",varchar(38),"Actieve actie 69",varchar(38),"Actieve actie 70",varchar(38),"Actieve actie 71",varchar(38),"Actieve actie 72",varchar(38),"Actieve actie 73",varchar(38),"Actieve actie 74",varchar(38),"Actieve actie 75",varchar(38),"Actieve actie 76",varchar(38),"Actieve actie 77",varchar(38),"Actieve actie 78",varchar(38),"Actuele actieve hoofdfase",varchar(20),"Actuele actieve subfase",varchar(21),"Actuele Status",varchar(29),"Afdeling (hoofdgroep)",varchar(13),"Besluit genomen 1. Verlening",varchar(10),"Besluit genomen 2. Steekproef",varchar(13),"Besluit genomen 3. Melding",varchar(10),"Besluit genomen 4. Vaststelling",varchar(13),"Besluit genomen Correcties",varchar(3),"Besluit genomen Correcties FB",varchar(3),"Besluit genomen Overige",varchar(3),Besluitvorming,varchar(19),Betaald,varchar(13),Boekjaar,varchar(24),csv_line_number,uint16,csv_number_of_fields,uint16,csv_total_number_of_columns,uint16,csv_type,varchar(8),"Datum besluit 1. Verlening",varchar(10),"Datum besluit 2. Steekproef",varchar(10),"Datum besluit 3. Melding",varchar(10),"Datum besluit 4. Vaststelling",varchar(10),"Datum besluit (jaar) 1. Verlening",varchar(13),"Datum besluit (jaar) 2. Steekproef",uint16,"Datum besluit (jaar) 3. Melding",varchar(13),"Datum besluit (jaar) 4. Vaststelling",uint16,"Datum besluit (jaar) Correcties",varchar(200),"Datum besluit (jaar) Correcties FB",varchar(200),"Datum besluit (jaar) Overige",varchar(200),"Datum besluit (maand) 1. Verlening",uint16,"Datum besluit (maand) 2. Steekproef",uint8,"Datum besluit (maand) 3. Melding",uint16,"Datum besluit (maand) 4. Vaststelling",uint8,"Datum besluit (maand) Correcties",varchar(200),"Datum besluit (maand) Correcties FB",varchar(200),"Datum besluit (maand) Overige",varchar(200),"Datum besluit (weeknummer) 1. Verlening",varchar(10),"Datum besluit (weeknummer) 2. Steekproef",uint8,"Datum besluit (weeknummer) 3. Melding",varchar(10),"Datum besluit (weeknummer) 4. Vaststelling",uint8,"Datum besluit (weeknummer) Correcties",varchar(200),"Datum besluit (weeknummer) Correcties FB",varchar(200),"Datum besluit (weeknummer) Overige",varchar(200),"Datum besluit Correcties",varchar(3),"Datum besluit Correcties FB",varchar(3),"Datum besluit Overige",varchar(3),"Deadline hoofdfase",varchar(10),"Documentnummer besluit 1. Verlening",varchar(13),"Documentnummer besluit 2. Steekproef",varchar(13),"Documentnummer besluit 3. Melding",varchar(13),"Documentnummer besluit 4. Vaststelling",varchar(13),"Documentnummer besluit Correcties",varchar(3),"Documentnummer besluit Correcties FB",varchar(3),"Documentnummer besluit Overige",varchar(200),"Doorlooptijd: 9.1.3. Inhoudelijk advies",uint8,"Doorlooptijd: 9.1.2. Juridisch advies",uint8,"Doorlooptijd: Declaratie indienen",uint16,"Doorlooptijd: Eindverantwoording (automatisch) opvragen",uint16,"Doorlooptijd: IBAN wijzigen",uint8,"Doorlooptijd: Intrekken aanvraag",uint8,"Doorlooptijd: Intrekken aanvraag00",uint8,"Doorlooptijd: Intrekken aanvraag01",uint16,"Doorlooptijd: Melding doorgeven",uint16,"Doorlooptijd: Tussenverantwoording (automatisch) opvragen",uint8,"Doorlooptijd: Vraag stellen / bericht sturen",varchar(11),"Doorlooptijd: Vraag stellen / bericht sturen00",uint8,"Einddatum activiteiten",varchar(10),"Einddatum taak",varchar(10),"Einddatum termijnbewaking",varchar(10),"Einddatum termijnbewaking 1. Verlening",varchar(20),"Einddatum termijnbewaking 2. Steekproef",varchar(10),"Einddatum termijnbewaking 3. Melding",varchar(20),"Einddatum termijnbewaking 4. Vaststelling",varchar(20),"Einddatum termijnbewaking Correcties",varchar(200),"Einddatum termijnbewaking Correcties FB",varchar(200),"Einddatum termijnbewaking Overige",varchar(200),"Einddatum termijnbewaking resterende dagen 1. Verlening",varchar(26),"Einddatum termijnbewaking resterende dagen 2. Steekproef",varchar(20),"Einddatum termijnbewaking resterende dagen 3. Melding",varchar(26),"Einddatum termijnbewaking resterende dagen 4. Vaststelling",varchar(21),"Einddatum termijnbewaking resterende dagen Correcties",varchar(200),"Einddatum termijnbewaking resterende dagen Correcties FB",varchar(200),"Einddatum termijnbewaking resterende dagen Overige",varchar(200),"Einddatum termijnbewaking resterende weken 1. Verlening",varchar(20),"Einddatum termijnbewaking resterende weken 2. Steekproef",varchar(20),"Einddatum termijnbewaking resterende weken 3. Melding",varchar(20),"Einddatum termijnbewaking resterende weken 4. Vaststelling",varchar(20),"Einddatum termijnbewaking resterende weken Correcties",varchar(200),"Einddatum termijnbewaking resterende weken Correcties FB",varchar(200),"Einddatum termijnbewaking resterende weken Overige",varchar(200),"Functioneel beheer",varchar(26),"Functioneel beheer - Groep",varchar(24),"Gebruiker 1",varchar(27),"Gebruiker 2",varchar(27),"Gebruiker 3",varchar(27),"Gebruiker 4",varchar(27),"Gebruiker 5",varchar(27),"Gebruiker 6",varchar(27),"Gebruiker 7",varchar(27),"Gebruiker 8",varchar(27),"Gebruiker 9",varchar(27),"Gebruiker 10",varchar(27),"Gebruiker 11",varchar(27),"Gebruiker 12",varchar(27),"Gebruiker 13",varchar(27),"Gebruiker 14",varchar(27),"Gebruiker 15",varchar(27),"Gebruiker 16",varchar(27),"Gebruiker 17",varchar(27),"Gebruiker 18",varchar(27),"Gebruiker 19",varchar(27),"Gebruiker 20",varchar(27),"Gebruiker 21",varchar(27),"Gebruiker 22",varchar(27),"Gebruiker 23",varchar(27),"Gebruiker 24",varchar(27),"Gebruiker 25",varchar(27),"Gebruiker 26",varchar(27),"Gebruiker 27",varchar(17),"Gebruiker 28",varchar(17),"Gebruiker 29",varchar(17),"Gebruiker 30",varchar(17),"Gebruiker 31",varchar(16),"Gebruiker 32",varchar(16),"Gebruiker 33",varchar(16),"Gebruiker 34",varchar(16),"Gebruiker 35",varchar(16),"Gebruiker 36",varchar(16),"Gebruiker 37",varchar(16),"Gebruiker 38",varchar(16),"Gebruiker 39",varchar(16),"Gebruiker 40",varchar(16),"Gebruiker 41",varchar(16),"Gebruiker 42",varchar(16),"Gebruiker 43",varchar(16),"Gebruiker 44",varchar(16),"Gebruiker 45",varchar(16),"Gebruiker 46",varchar(16),"Gebruiker 47",varchar(16),"Gebruiker 48",varchar(16),"Gebruiker 49",varchar(16),"Gebruiker 50",varchar(16),"Gebruiker 51",varchar(16),"Gebruiker 52",varchar(16),"Gebruiker 53",varchar(16),"Gebruiker 54",varchar(16),"Gebruiker 55",varchar(16),"Gebruiker 56",varchar(16),"Gebruiker 57",varchar(16),"Gebruiker 58",varchar(16),"Gebruiker 59",varchar(16),"Gebruiker 60",varchar(16),"Gebruiker 61",varchar(16),"Gebruiker 62",varchar(16),"Gebruiker 63",varchar(16),"Gebruiker 64",varchar(16),"Gebruiker 65",varchar(16),"Gebruiker 66",varchar(16),"Gebruiker 67",varchar(16),"Gebruiker 68",varchar(16),"Gebruiker 69",varchar(16),"Gebruiker 70",varchar(16),"Gebruiker 71",varchar(16),"Gebruiker 72",varchar(16),"Gebruiker 73",varchar(16),"Gebruiker 74",varchar(16),"Gebruiker 75",varchar(16),"Gebruiker 76",varchar(16),"Gebruiker 77",varchar(16),"Gebruiker 78",varchar(16),"Gebruikersrol 1",varchar(34),"Gebruikersrol 2",varchar(33),"Gebruikersrol 3",varchar(17),"Gebruikersrol 4",varchar(17),"Gebruikersrol 5",varchar(17),"Gebruikersrol 6",varchar(17),"Gebruikersrol 7",varchar(17),"Gebruikersrol 8",varchar(17),"Gebruikersrol 9",varchar(17),"Gebruikersrol 10",varchar(17),"Gebruikersrol 11",varchar(17),"Gebruikersrol 12",varchar(17),"Gebruikersrol 13",varchar(17),"Gebruikersrol 14",varchar(17),"Gebruikersrol 15",varchar(17),"Gebruikersrol 16",varchar(17),"Gebruikersrol 17",varchar(17),"Gebruikersrol 18",varchar(17),"Gebruikersrol 19",varchar(8),"Gebruikersrol 20",varchar(8),"Gebruikersrol 21",varchar(8),"Gebruikersrol 22",varchar(8),"Gebruikersrol 23",varchar(8),"Gebruikersrol 24",varchar(8),"Gebruikersrol 25",varchar(8),"Gebruikersrol 26",varchar(8),"Gebruikersrol 27",varchar(17),"Gebruikersrol 28",varchar(17),"Gebruikersrol 29",varchar(17),"Gebruikersrol 30",varchar(17),"Gebruikersrol 31",varchar(11),"Gebruikersrol 32",varchar(8),"Gebruikersrol 33",varchar(8),"Gebruikersrol 34",varchar(8),"Gebruikersrol 35",varchar(8),"Gebruikersrol 36",varchar(8),"Gebruikersrol 37",varchar(8),"Gebruikersrol 38",varchar(8),"Gebruikersrol 39",varchar(8),"Gebruikersrol 40",varchar(8),"Gebruikersrol 41",varchar(8),"Gebruikersrol 42",varchar(8),"Gebruikersrol 43",varchar(8),"Gebruikersrol 44",varchar(8),"Gebruikersrol 45",varchar(8),"Gebruikersrol 46",varchar(8),"Gebruikersrol 47",varchar(8),"Gebruikersrol 48",varchar(8),"Gebruikersrol 49",varchar(8),"Gebruikersrol 50",varchar(8),"Gebruikersrol 51",varchar(8),"Gebruikersrol 52",varchar(8),"Gebruikersrol 53",varchar(8),"Gebruikersrol 54",varchar(8),"Gebruikersrol 55",varchar(8),"Gebruikersrol 56",varchar(8),"Gebruikersrol 57",varchar(8),"Gebruikersrol 58",varchar(8),"Gebruikersrol 59",varchar(8),"Gebruikersrol 60",varchar(8),"Gebruikersrol 61",varchar(8),"Gebruikersrol 62",varchar(8),"Gebruikersrol 63",varchar(8),"Gebruikersrol 64",varchar(8),"Gebruikersrol 65",varchar(8),"Gebruikersrol 66",varchar(8),"Gebruikersrol 67",varchar(8),"Gebruikersrol 68",varchar(8),"Gebruikersrol 69",varchar(8),"Gebruikersrol 70",varchar(8),"Gebruikersrol 71",varchar(8),"Gebruikersrol 72",varchar(8),"Gebruikersrol 73",varchar(8),"Gebruikersrol 74",varchar(8),"Gebruikersrol 75",varchar(8),"Gebruikersrol 76",varchar(8),"Gebruikersrol 77",varchar(8),"Gebruikersrol 78",varchar(8),"Gegenereerd veld handmatig ingevuld",varchar(19),Gemachtigde,varchar(200),"Gemachtigde ID",varchar(200),"Huidig definitief besluit",varchar(26),"Opschorting 1",uint16,"Opschorting 2",uint16,"Opschorting 3",uint8,"Opschorting 4",varchar(12),"Opschorting fase 1",varchar(15),"Opschorting fase 2",varchar(15),"Opschorting fase 3",varchar(15),"Opschorting fase 4",varchar(12),"Organisatie ID",varchar(24),"Organisatie naam",varchar(186),"Periodiciteit activiteiten",varchar(18),"Portefeuillehouder (monitoring)",varchar(33),"Portefeuillehouder (vaststelling)",varchar(28),"Portefeuillehouder (verlening)",varchar(102),"Project Assistent",varchar(65),"Project Assistent - Groep",varchar(27),"Regeling ID",varchar(24),Regelingnaam,varchar(184),Regelingnummer,uint8,"RVO dossiernummer",uint32,Saldo,varchar(13),SAS-Conversiedossier,varchar(2),SAS-Dossiernummer,varchar(14),SAS-Regeling,varchar(137),"SharePoint nummer",varchar(12),"Startdatum activiteiten",varchar(45),"Startdatum termijnbewaking 1. Verlening",varchar(10),"Startdatum termijnbewaking 2. Steekproef",varchar(10),"Startdatum termijnbewaking 3. Melding",varchar(10),"Startdatum termijnbewaking 4. Vaststelling",varchar(10),"Startdatum termijnbewaking Correcties",varchar(200),"Startdatum termijnbewaking Correcties FB",varchar(200),"Startdatum termijnbewaking Overige",varchar(200),"Status termijnbewaking 1. Verlening",varchar(26),"Status termijnbewaking 2. Steekproef",varchar(26),"Status termijnbewaking 3. Melding",varchar(26),"Status termijnbewaking 4. Vaststelling",varchar(26),"Status termijnbewaking Correcties",varchar(200),"Status termijnbewaking Correcties FB",varchar(200),"Status termijnbewaking Overige",varchar(200),"Statuskleur termijnbewaking actieve hoofdfase",varchar(10),"Stemlijst besluit",varchar(200),"Stemlijst resultaat",varchar(200),"Subsidietype (Jaarlijks of eenmalig)",varchar(18),"Team (subgroep)",varchar(19),"Termijnbewaking verdaagd 1. Verlening",varchar(26),"Termijnbewaking verdaagd 2. Steekproef",varchar(10),"Termijnbewaking verdaagd 3. Melding",varchar(26),"Termijnbewaking verdaagd 4. Vaststelling",varchar(3),"Termijnbewaking verdaagd Correcties",varchar(200),"Termijnbewaking verdaagd Correcties FB",varchar(200),"Termijnbewaking verdaagd Overige",varchar(10),"Titel aanvraag",varchar(451),"Vastgesteld bedrag",varchar(12),Vaststeller,varchar(47),"Vaststeller - Groep",varchar(19),"Vergadering besluit",varchar(200),"Vergadering dossier nummer",varchar(200),"Verleend bedrag (of bedrag na herziening tussentijds)",varchar(13),Verlener,varchar(64),"Verlener - Groep",varchar(40),Vrijval,varchar(18)
    -> Clean_column_names [lowercase_attributes_Input]
Clean_column_names: clean_column_names
    only_retain_letters_number_underscores_Output -> Convert_float_columns [StringReplacer_verwijder_tekens_Input]

Bookmark: Aanpassing: aangevraagd_bedrag & verleend_bedrag_of_bedrag_na_herziening_tussentijds & vastgesteld_bedrag
Convert_float_columns: convert_float_columns
    _FLOAT_COLUMNS = aangevraagd_bedrag,vastgesteld_bedrag,verleend_bedrag_of_bedrag_na_herziening_tussentijds
    ConvertFloatColumns_output -> AttributeManager
AttributeManager
    -> AttributeCreator_3
AttributeCreator_3
    ATTR_TABLE = SET_TO privacy (varchar(200)) = $(_meta_privacy)
    -> DateTimeConverter_4

Bookmark: Datumvelden
DateTimeConverter_4
    DATETIME_ATTR = aanvraagdatum00
    IN_FORMAT = %d-%m-%Y %T
    OUT_FORMAT = %Y-%m-%d %H:%M:%S
    PASSTHROUGH = YES
    REPAIR_INPUT = YES
    TEST_INPUT = 08-04-2025 20:34:55
    -> DateTimeConverter_3
DateTimeConverter_3
    DATETIME_ATTR = einddatum_activiteiten einddatum_taak einddatum_termijnbewaking
    IN_FORMAT = %d-%m-%Y
    OUT_FORMAT = %Y-%m-%d
    PASSTHROUGH = YES
    REPAIR_INPUT = YES
    -> subsidies (writer MSSQL_AZURE_2)

Bookmark: Wegschrijven
subsidies (writer MSSQL_AZURE_2)
    attributes: privacy varchar(200), aan_zet varchar(183), aangevraagd_bedrag float, aangevraagd_via varchar(19), aanvraag_id varchar(24),PrimaryKey, aanvraagdatum varchar(17), aanvraagdatum00 varchar_max, aanvraagdatum_jaar varchar(10), aanvraagdatum_maand integer, aanvraagdatum_weeknummer varchar(3), aanvraagnummer varchar(9), aanvraagwijze_particulier__organisatie varchar(15), aanvrager_id varchar(24), aanvrager_naam varchar(88), actiestatus_medewerkers varchar(15), actieve_actie_1 varchar(79), actieve_actie_2 varchar(79), actieve_actie_3 varchar(60), actieve_actie_4 varchar(79), actieve_actie_5 varchar(79), actieve_actie_6 varchar(60), actieve_actie_7 varchar(79), actieve_actie_8 varchar(60), actieve_actie_9 varchar(60), actieve_actie_10 varchar(79), actieve_actie_11 varchar(79), actieve_actie_12 varchar(79), actieve_actie_13 varchar(60), actieve_actie_14 varchar(60), actieve_actie_15 varchar(60),
      actieve_actie_16 varchar(57), actieve_actie_17 varchar(57), actieve_actie_18 varchar(57), actieve_actie_19 varchar(38), actieve_actie_20 varchar(38), actieve_actie_21 varchar(38), actieve_actie_22 varchar(38), actieve_actie_23 varchar(38), actieve_actie_24 varchar(38), actieve_actie_25 varchar(38), actieve_actie_26 varchar(38), actieve_actie_27 varchar(50), actieve_actie_28 varchar(50), actieve_actie_29 varchar(50), actieve_actie_30 varchar(50), actieve_actie_31 varchar(38), actieve_actie_32 varchar(38), actieve_actie_33 varchar(38), actieve_actie_34 varchar(38), actieve_actie_35 varchar(38), actieve_actie_36 varchar(38), actieve_actie_37 varchar(38), actieve_actie_38 varchar(38), actieve_actie_39 varchar(38), actieve_actie_40 varchar(38), actieve_actie_41 varchar(38), actieve_actie_42 varchar(38), actieve_actie_43 varchar(38), actieve_actie_44 varchar(38), actieve_actie_45 varchar(38),
      actieve_actie_46 varchar(38), actieve_actie_47 varchar(38), actieve_actie_48 varchar(38), actieve_actie_49 varchar(38), actieve_actie_50 varchar(38), actieve_actie_51 varchar(38), actieve_actie_52 varchar(38), actieve_actie_53 varchar(38), actieve_actie_54 varchar(38), actieve_actie_55 varchar(38), actieve_actie_56 varchar(38), actieve_actie_57 varchar(38), actieve_actie_58 varchar(38), actieve_actie_59 varchar(38), actieve_actie_60 varchar(38), actieve_actie_61 varchar(38), actieve_actie_62 varchar(38), actieve_actie_63 varchar(38), actieve_actie_64 varchar(38), actieve_actie_65 varchar(38), actieve_actie_66 varchar(38), actieve_actie_67 varchar(38), actieve_actie_68 varchar(38), actieve_actie_69 varchar(38), actieve_actie_70 varchar(38), actieve_actie_71 varchar(38), actieve_actie_72 varchar(38), actieve_actie_73 varchar(38), actieve_actie_74 varchar(38), actieve_actie_75 varchar(38),
      actieve_actie_76 varchar(38), actieve_actie_77 varchar(38), actieve_actie_78 varchar(38), actuele_actieve_hoofdfase varchar(20), actuele_actieve_subfase varchar(21), actuele_status varchar(29), afdeling_hoofdgroep varchar(13), besluit_genomen_1_verlening varchar(10), besluit_genomen_2_steekproef varchar(13), besluit_genomen_3_melding varchar(10), besluit_genomen_4_vaststelling varchar(13), besluit_genomen_correcties varchar(3), besluit_genomen_correcties_fb varchar(3), besluit_genomen_overige varchar(3), besluitvorming varchar(19), betaald varchar(13), boekjaar varchar(24), datum_besluit_1_verlening varchar(10), datum_besluit_2_steekproef varchar(10), datum_besluit_3_melding varchar(10), datum_besluit_4_vaststelling varchar(10), datum_besluit_jaar_1_verlening varchar(13), datum_besluit_jaar_2_steekproef integer, datum_besluit_jaar_3_melding varchar(13), datum_besluit_jaar_4_vaststelling integer, datum_besluit_jaar_correcties varchar(200), datum_besluit_jaar_correcties_fb varchar(200), datum_besluit_jaar_overige varchar(200), datum_besluit_maand_1_verlening integer, datum_besluit_maand_2_steekproef tinyint,
      datum_besluit_maand_3_melding integer, datum_besluit_maand_4_vaststelling tinyint, datum_besluit_maand_correcties varchar(200), datum_besluit_maand_correcties_fb varchar(200), datum_besluit_maand_overige varchar(200), datum_besluit_weeknummer_1_verlening varchar(10), datum_besluit_weeknummer_2_steekproef tinyint, datum_besluit_weeknummer_3_melding varchar(10), datum_besluit_weeknummer_4_vaststelling tinyint, datum_besluit_weeknummer_correcties varchar(200), datum_besluit_weeknummer_correcties_fb varchar(200), datum_besluit_weeknummer_overige varchar(200), datum_besluit_correcties varchar(3), datum_besluit_correcties_fb varchar(3), datum_besluit_overige varchar(3), deadline_hoofdfase varchar(10), documentnummer_besluit_1_verlening varchar(13), documentnummer_besluit_2_steekproef varchar(13), documentnummer_besluit_3_melding varchar(13), documentnummer_besluit_4_vaststelling varchar(13), documentnummer_besluit_correcties varchar(3), documentnummer_besluit_correcties_fb varchar(3), documentnummer_besluit_overige varchar(200), doorlooptijd_913_inhoudelijk_advies tinyint, doorlooptijd_912_juridisch_advies tinyint, doorlooptijd_declaratie_indienen integer, doorlooptijd_eindverantwoording_automatisch_opvragen integer, doorlooptijd_iban_wijzigen tinyint, doorlooptijd_intrekken_aanvraag tinyint, doorlooptijd_intrekken_aanvraag00 tinyint,
      doorlooptijd_intrekken_aanvraag01 integer, doorlooptijd_melding_doorgeven integer, doorlooptijd_tussenverantwoording_automatisch_opvragen tinyint, doorlooptijd_vraag_stellen__bericht_sturen varchar(11), doorlooptijd_vraag_stellen__bericht_sturen00 tinyint, einddatum_activiteiten varchar_max, einddatum_taak varchar_max, einddatum_termijnbewaking varchar_max, einddatum_termijnbewaking_1_verlening varchar(20), einddatum_termijnbewaking_2_steekproef varchar(10), einddatum_termijnbewaking_3_melding varchar(20), einddatum_termijnbewaking_4_vaststelling varchar(20), einddatum_termijnbewaking_correcties varchar(200), einddatum_termijnbewaking_correcties_fb varchar(200), einddatum_termijnbewaking_overige varchar(200), einddatum_termijnbewaking_resterende_dagen_1_verlening varchar(26), einddatum_termijnbewaking_resterende_dagen_2_steekproef varchar(20), einddatum_termijnbewaking_resterende_dagen_3_melding varchar(26), einddatum_termijnbewaking_resterende_dagen_4_vaststelling varchar(21), einddatum_termijnbewaking_resterende_dagen_correcties varchar(200), einddatum_termijnbewaking_resterende_dagen_correcties_fb varchar(200), einddatum_termijnbewaking_resterende_dagen_overige varchar(200), einddatum_termijnbewaking_resterende_weken_1_verlening varchar(20), einddatum_termijnbewaking_resterende_weken_2_steekproef varchar(20), einddatum_termijnbewaking_resterende_weken_3_melding varchar(20), einddatum_termijnbewaking_resterende_weken_4_vaststelling varchar(20), einddatum_termijnbewaking_resterende_weken_correcties varchar(200), einddatum_termijnbewaking_resterende_weken_correcties_fb varchar(200), einddatum_termijnbewaking_resterende_weken_overige varchar(200), functioneel_beheer varchar(26),
      functioneel_beheer__groep varchar(24), gebruiker_1 varchar(27), gebruiker_2 varchar(27), gebruiker_3 varchar(27), gebruiker_4 varchar(27), gebruiker_5 varchar(27), gebruiker_6 varchar(27), gebruiker_7 varchar(27), gebruiker_8 varchar(27), gebruiker_9 varchar(27), gebruiker_10 varchar(27), gebruiker_11 varchar(27), gebruiker_12 varchar(27), gebruiker_13 varchar(27), gebruiker_14 varchar(27), gebruiker_15 varchar(27), gebruiker_16 varchar(27), gebruiker_17 varchar(27), gebruiker_18 varchar(27), gebruiker_19 varchar(27), gebruiker_20 varchar(27), gebruiker_21 varchar(27), gebruiker_22 varchar(27), gebruiker_23 varchar(27), gebruiker_24 varchar(27), gebruiker_25 varchar(27), gebruiker_26 varchar(27), gebruiker_27 varchar(17), gebruiker_28 varchar(17), gebruiker_29 varchar(17),
      gebruiker_30 varchar(17), gebruiker_31 varchar(16), gebruiker_32 varchar(16), gebruiker_33 varchar(16), gebruiker_34 varchar(16), gebruiker_35 varchar(16), gebruiker_36 varchar(16), gebruiker_37 varchar(16), gebruiker_38 varchar(16), gebruiker_39 varchar(16), gebruiker_40 varchar(16), gebruiker_41 varchar(16), gebruiker_42 varchar(16), gebruiker_43 varchar(16), gebruiker_44 varchar(16), gebruiker_45 varchar(16), gebruiker_46 varchar(16), gebruiker_47 varchar(16), gebruiker_48 varchar(16), gebruiker_49 varchar(16), gebruiker_50 varchar(16), gebruiker_51 varchar(16), gebruiker_52 varchar(16), gebruiker_53 varchar(16), gebruiker_54 varchar(16), gebruiker_55 varchar(16), gebruiker_56 varchar(16), gebruiker_57 varchar(16), gebruiker_58 varchar(16), gebruiker_59 varchar(16),
      gebruiker_60 varchar(16), gebruiker_61 varchar(16), gebruiker_62 varchar(16), gebruiker_63 varchar(16), gebruiker_64 varchar(16), gebruiker_65 varchar(16), gebruiker_66 varchar(16), gebruiker_67 varchar(16), gebruiker_68 varchar(16), gebruiker_69 varchar(16), gebruiker_70 varchar(16), gebruiker_71 varchar(16), gebruiker_72 varchar(16), gebruiker_73 varchar(16), gebruiker_74 varchar(16), gebruiker_75 varchar(16), gebruiker_76 varchar(16), gebruiker_77 varchar(16), gebruiker_78 varchar(16), gebruikersrol_1 varchar(34), gebruikersrol_2 varchar(33), gebruikersrol_3 varchar(17), gebruikersrol_4 varchar(17), gebruikersrol_5 varchar(17), gebruikersrol_6 varchar(17), gebruikersrol_7 varchar(17), gebruikersrol_8 varchar(17), gebruikersrol_9 varchar(17), gebruikersrol_10 varchar(17), gebruikersrol_11 varchar(17),
      gebruikersrol_12 varchar(17), gebruikersrol_13 varchar(17), gebruikersrol_14 varchar(17), gebruikersrol_15 varchar(17), gebruikersrol_16 varchar(17), gebruikersrol_17 varchar(17), gebruikersrol_18 varchar(17), gebruikersrol_19 varchar(8), gebruikersrol_20 varchar(8), gebruikersrol_21 varchar(8), gebruikersrol_22 varchar(8), gebruikersrol_23 varchar(8), gebruikersrol_24 varchar(8), gebruikersrol_25 varchar(8), gebruikersrol_26 varchar(8), gebruikersrol_27 varchar(17), gebruikersrol_28 varchar(17), gebruikersrol_29 varchar(17), gebruikersrol_30 varchar(17), gebruikersrol_31 varchar(11), gebruikersrol_32 varchar(8), gebruikersrol_33 varchar(8), gebruikersrol_34 varchar(8), gebruikersrol_35 varchar(8), gebruikersrol_36 varchar(8), gebruikersrol_37 varchar(8), gebruikersrol_38 varchar(8), gebruikersrol_39 varchar(8), gebruikersrol_40 varchar(8), gebruikersrol_41 varchar(8),
      gebruikersrol_42 varchar(8), gebruikersrol_43 varchar(8), gebruikersrol_44 varchar(8), gebruikersrol_45 varchar(8), gebruikersrol_46 varchar(8), gebruikersrol_47 varchar(8), gebruikersrol_48 varchar(8), gebruikersrol_49 varchar(8), gebruikersrol_50 varchar(8), gebruikersrol_51 varchar(8), gebruikersrol_52 varchar(8), gebruikersrol_53 varchar(8), gebruikersrol_54 varchar(8), gebruikersrol_55 varchar(8), gebruikersrol_56 varchar(8), gebruikersrol_57 varchar(8), gebruikersrol_58 varchar(8), gebruikersrol_59 varchar(8), gebruikersrol_60 varchar(8), gebruikersrol_61 varchar(8), gebruikersrol_62 varchar(8), gebruikersrol_63 varchar(8), gebruikersrol_64 varchar(8), gebruikersrol_65 varchar(8), gebruikersrol_66 varchar(8), gebruikersrol_67 varchar(8), gebruikersrol_68 varchar(8), gebruikersrol_69 varchar(8), gebruikersrol_70 varchar(8), gebruikersrol_71 varchar(8),
      gebruikersrol_72 varchar(8), gebruikersrol_73 varchar(8), gebruikersrol_74 varchar(8), gebruikersrol_75 varchar(8), gebruikersrol_76 varchar(8), gebruikersrol_77 varchar(8), gebruikersrol_78 varchar(8), gegenereerd_veld_handmatig_ingevuld varchar(19), gemachtigde varchar(200), gemachtigde_id varchar(200), huidig_definitief_besluit varchar(26), opschorting_1 integer, opschorting_2 integer, opschorting_3 tinyint, opschorting_4 varchar(12), opschorting_fase_1 varchar(15), opschorting_fase_2 varchar(15), opschorting_fase_3 varchar(15), opschorting_fase_4 varchar(12), organisatie_id varchar(24), organisatie_naam varchar(186), periodiciteit_activiteiten varchar(18), portefeuillehouder_monitoring varchar(33), portefeuillehouder_vaststelling varchar(28), portefeuillehouder_verlening varchar(102), project_assistent varchar(65), project_assistent__groep varchar(27), regeling_id varchar(24), regelingnaam varchar(184), regelingnummer tinyint,
      rvo_dossiernummer bigint, saldo varchar(13), sasconversiedossier varchar(2), sasdossiernummer varchar(14), sasregeling varchar(137), sharepoint_nummer varchar(12), startdatum_activiteiten varchar(45), startdatum_termijnbewaking_1_verlening varchar(10), startdatum_termijnbewaking_2_steekproef varchar(10), startdatum_termijnbewaking_3_melding varchar(10), startdatum_termijnbewaking_4_vaststelling varchar(10), startdatum_termijnbewaking_correcties varchar(200), startdatum_termijnbewaking_correcties_fb varchar(200), startdatum_termijnbewaking_overige varchar(200), status_termijnbewaking_1_verlening varchar(26), status_termijnbewaking_2_steekproef varchar(26), status_termijnbewaking_3_melding varchar(26), status_termijnbewaking_4_vaststelling varchar(26), status_termijnbewaking_correcties varchar(200), status_termijnbewaking_correcties_fb varchar(200), status_termijnbewaking_overige varchar(200), statuskleur_termijnbewaking_actieve_hoofdfase varchar(10), stemlijst_besluit varchar(200), stemlijst_resultaat varchar(200), subsidietype_jaarlijks_of_eenmalig varchar(18), team_subgroep varchar(19), termijnbewaking_verdaagd_1_verlening varchar(26), termijnbewaking_verdaagd_2_steekproef varchar(10), termijnbewaking_verdaagd_3_melding varchar(26), termijnbewaking_verdaagd_4_vaststelling varchar(3),
      termijnbewaking_verdaagd_correcties varchar(200), termijnbewaking_verdaagd_correcties_fb varchar(200), termijnbewaking_verdaagd_overige varchar(10), titel_aanvraag varchar(451), vastgesteld_bedrag varchar(12), vaststeller varchar(47), vaststeller__groep varchar(19), vergadering_besluit varchar(200), vergadering_dossier_nummer varchar(200), verleend_bedrag_of_bedrag_na_herziening_tussentijds varchar(13), verlener varchar(64), verlener__groep varchar(40), vrijval varchar(18)
