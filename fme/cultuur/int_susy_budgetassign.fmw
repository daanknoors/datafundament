FME workspace int_susy_budgetassign.fmw

Parameters:
- _meta_privacy = geen_persoonsgegevens   # privacy
- _Azure_Container = raw   # Container input bestand(en)
- _Azure_Folder = staging/Susy/   # Pad naar input bestand(en) in Azure
- DestDataset_MSSQL_AZURE_5 = Microsoft Azure SQL server df   # Azure SQL Database Connection

Writers:
- MSSQL_AZURE_4: MSSQL_AZURE to $(DestDataset_MSSQL_AZURE_5)

Bookmark: BudgetAssign
Load_csv_file_budget_2: load_csv_from_blob
    _FME_AZURE_CONTAINER = $(_Azure_Container)
    _FME_Azure_Folder = $(_Azure_Folder)
    _Filename = budgetAssign.csv
    Load_CSV_Output -> AttributeExposer_3
AttributeExposer_3
    ATTR_TABLE = Aanvraagnummer,varchar(9),Boekjaar,varchar(200),"Budget boekjaren",varchar(11),Budgetbedrag,varchar(13),BudgetId,varchar(24),Budgetnaam,varchar(277),csv_line_number,uint16,csv_number_of_fields,uint8,csv_total_number_of_columns,uint8,csv_type,varchar(8),Doelstelling,varchar(25),"Naam WBS",varchar(200),"Nummer WBS",varchar(200),"SharePoint nummer",varchar(12),Vastgesteld,varchar(12),"Vergadering dossier nummer",varchar(200),Verleend,varchar(13)
    -> Clean_column_names_4 [lowercase_attributes_Input]
Clean_column_names_4: clean_column_names
    only_retain_letters_number_underscores_Output -> Convert_float_columns_3 [StringReplacer_verwijder_tekens_Input]
Convert_float_columns_3: convert_float_columns
    _FLOAT_COLUMNS = budgetbedrag
    ConvertFloatColumns_output -> CRCCalculator_3
budgetassign (writer MSSQL_AZURE_4)
    attributes: aanvraagnummer varchar(9), boekjaar varchar(200), budget_boekjaren varchar(11), budgetbedrag varchar(13), budgetid varchar(24), budgetnaam varchar(277), doelstelling varchar(25), naam_wbs varchar(200), nummer_wbs varchar(200), sharepoint_nummer varchar(12), vastgesteld varchar(12), vergadering_dossier_nummer varchar(200), verleend varchar(13), hash_key char(16),PrimaryKey

Bookmark: Add hash identifier and remove duplicates
CRCCalculator_3
    ALG_TYPE = MD5
    CRC_ATTR = hash_key
    CRC_TYPE = ALL_ATTRS_ENCODED
    ALG_CHOICES = MD5
    -> DuplicateFilter_2
DuplicateFilter_2
    INPUT_ORDERED_CHOICE_LOOKUP = NO
    KEYATTR = hash_key
    INPUT_ORDERED_CHOICE = No
    UNIQUE -> budgetassign (writer MSSQL_AZURE_4)
