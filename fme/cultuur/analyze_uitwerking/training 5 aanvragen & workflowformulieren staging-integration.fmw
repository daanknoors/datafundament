FME workspace training 5 aanvragen & workflowformulieren staging-integration.fmw
Title: Test

Parameters:
- CONTAINER_IN = training-synpase   # Container input bestand(en)
- FOLDER_NAME_IN = staging/ronny/   # Pad naar input bestand(en) in Azure
- _meta_privacy = geen_persoonsgegevens
- DestDataset_MSSQL_AZURE = sql server   # Azure SQL Database Connection
- DestDataset_MSSQL_AZURE_7 = Microsoft Azure SQL server df   # Azure SQL Database Connection
- DestDataset_MSSQL_AZURE_3 = Microsoft Azure SQL server df   # Azure SQL Database Connection

Writers:
- MSSQL_AZURE_1: MSSQL_AZURE to $(DestDataset_MSSQL_AZURE)
- MSSQL_AZURE_4: MSSQL_AZURE to $(DestDataset_MSSQL_AZURE_7)
- MSSQL_AZURE_2: MSSQL_AZURE to $(DestDataset_MSSQL_AZURE_3)

Note: Controleren op: / -nulwaarden/missing / -Juiste datatype / - Datumvelden aanpassen / - Ja/Nee omzetten naar boolean?

Bookmark: Aanvragen: Lijst met data ophalen uit Blobstorage
Creator_3
    GEOMTYPE = Geometry Object
    NUM = 1
    CREATED -> AzureBlobStorageConnector_2
AzureBlobStorageConnector_2
    CREDENTIAL_SOURCE = WEBCONN
    OPERATION_TYPE = List
    PARAMETER_SETUP = _FME_AZURE_CONTAINER][{"display":"training-synpase","value":"training-synpase"}]]_FME_FILES][{"display":"staging/ronny/","value":"staging/ronny/"}]]_FME_INCLUDE_SUBFOLDERS]No]_FME_ATTRIBUTES_TO_ADD]"_url _full_path _name _created"]FME_CONTROLLER_QUERY_FILE]]FME_CONTROLLER_CHOICE]List
    _FME_AZURE_CONNECTION = Blob
    -> Tester

Bookmark: Kies meest recente bestand
Tester
    BOOL_OP = OR
    TEST_CLAUSE = CASE_INSENSITIVE_TEST @Value(_name) CONTAINS aanvragen
    TEST_MODE = CASE_INSENSITIVE_TEST
    PASSED -> Sorter
Sorter
    SORT_PARM = _created NATURAL DESCENDING
    SORTED -> FeatureReader_2 [INITIATOR]

Bookmark: Haal het bestand op mbv url
FeatureReader_2
    ATTR_ACCUM_MODE = Only Use Result
    COMBINE_GEOM = Use Result
    DATASET = @Value(_url)
    FORMAT = PARQUET
    INITIATOR_FIRST_OUTPUT = default
    ORDER_RESULTS = No
    OUTPUT_ADD_SCHEMA_ATTRIBUTES = NO
    OUTPUT_FEATURES_DISPLAY = Schema and Data Features
    PARQUET_SUPPORT_ANNOTATED_LISTS = yes
    PARQUET_SUPPORT_GEOMETRY = yes
    PARQUET_SUPPORT_LISTS = yes
    PARQUET_SUPPORT_LOCAL_TIME = yes
    <OTHER> -> AttributeExposer_2
Note: Maak attributen zichtbaar
AttributeExposer_2
    ATTR_TABLE = aan_zet,varchar(179),aangevraagd_bedrag,varchar(17),aangevraagd_via,varchar(12),aanvraag_id,varchar(24),aanvraagdatum,varchar(19),aanvraagdatum_jaar,uint16,aanvraagdatum_maand,uint8,aanvraagdatum_weeknummer,uint8,aanvraagnummer,varchar(9),aanvraagwijze_particulier_/_organisatie,varchar(11),aanvrager_id,varchar(24),aanvrager_naam,varchar(14),actiestatus_medewerkers,varchar(14),actieve__actie_11,varchar(79),actieve_actie_1,varchar(79),actieve_actie_2,varchar(79),actieve_actie_3,varchar(79),actieve_actie_4,varchar(79),actieve_actie_5,varchar(79),actieve_actie_6,varchar(60),actieve_actie_7,varchar(79),actieve_actie_8,varchar(60),actieve_actie_9,varchar(79),actieve_actie_10,varchar(60),actieve_actie_12,varchar(79),actieve_actie_13,varchar(60),actieve_actie_14,varchar(60),actieve_actie_15,varchar(60),actieve_actie_16,varchar(32),actieve_actie_17,varchar(34),actieve_actie_18,varchar(16),actieve_actie_19,varchar(17),actieve_actie_20,varchar(26),actieve_actie_21,varchar(14),actieve_actie_22,varchar(14),actieve_actie_23,varchar(33),actieve_actie_24,varchar(14),actieve_actie_25,varchar(33),actieve_actie_26,varchar(33),actieve_actie_27,varchar(50),actieve_actie_28,varchar(50),actieve_actie_29,varchar(50),actieve_actie_30,varchar(50),actieve_actie_31,varchar(24),actuele_actieve_hoofdfase,varchar(15),actuele_actieve_subfase,varchar(21),actuele_status,varchar(29),afdeling_hoofdgroep,varchar(12),besluit_genomen_1_verlening,varchar(3),besluit_genomen_2_steekproef,varchar(3),besluit_genomen_3_melding,varchar(3),besluit_genomen_4_vaststelling,varchar(3),besluit_genomen_correcties,varchar(3),besluit_genomen_correcties_fb,varchar(3),besluit_genomen_overige,varchar(3),besluitvorming,varchar(19),betaald,varchar(13),boekjaar,varchar(24),datum_besluit_1_verlening,varchar(10),datum_besluit_2_steekproef,varchar(10),datum_besluit_3_melding,varchar(10),datum_besluit_4_vaststelling,varchar(10),datum_besluit_correcties,varchar(200),datum_besluit_correcties_fb,varchar(200),datum_besluit_jaar_1_verlening,uint16,datum_besluit_jaar_2_steekproef,uint16,datum_besluit_jaar_3_melding,uint16,datum_besluit_jaar_4_vaststelling,uint16,datum_besluit_jaar_correcties,varchar(200),datum_besluit_jaar_correcties_fb,varchar(200),datum_besluit_jaar_overige,varchar(200),datum_besluit_maand_1_verlening,uint8,datum_besluit_maand_2_steekproef,uint8,datum_besluit_maand_3_melding,uint8,datum_besluit_maand_4_vaststelling,uint8,datum_besluit_maand_correcties,varchar(200),datum_besluit_maand_correcties_fb,varchar(200),datum_besluit_maand_overige,varchar(200),datum_besluit_overige,varchar(200),datum_besluit_weeknummer_1_verlening,uint8,datum_besluit_weeknummer_2_steekproef,uint8,datum_besluit_weeknummer_3_melding,uint8,datum_besluit_weeknummer_4_vaststelling,uint8,datum_besluit_weeknummer_correcties,varchar(200),datum_besluit_weeknummer_correcties_fb,varchar(200),datum_besluit_weeknummer_overige,varchar(200),deadline_hoofdfase,varchar(10),documentnummer_besluit_1_verlening,varchar(13),documentnummer_besluit_2_steekproef,varchar(13),documentnummer_besluit_3_melding,varchar(13),documentnummer_besluit_4_vaststelling,varchar(13),documentnummer_besluit_correcties,varchar(200),documentnummer_besluit_correcties_fb,varchar(200),documentnummer_besluit_overige,varchar(200),doorlooptijd:_912_juridisch_advies,uint8,doorlooptijd:_913_inhoudelijk_advies,uint8,doorlooptijd:_declaratie_indienen,uint16,doorlooptijd:_eindverantwoording_automatisch_opvragen,uint8,doorlooptijd:_iban_wijzigen,uint8,doorlooptijd:_intrekken_aanvraag,uint8,doorlooptijd:_melding_doorgeven,uint16,doorlooptijd:_tussenverantwoording_automatisch_opvragen,uint8,doorlooptijd:_vraag_stellen_/_bericht_sturen,uint8,einddatum_activiteiten,varchar(10),einddatum_taak,varchar(10),einddatum_termijnbewaking,varchar(10),einddatum_termijnbewaking_1_verlening,varchar(10),einddatum_termijnbewaking_2_steekproef,varchar(10),einddatum_termijnbewaking_3_melding,varchar(10),einddatum_termijnbewaking_4_vaststelling,varchar(10),einddatum_termijnbewaking_correcties,varchar(200),einddatum_termijnbewaking_correcties_fb,varchar(200),einddatum_termijnbewaking_overige,varchar(200),einddatum_termijnbewaking_resterende_dagen_1_verlening,varchar(20),einddatum_termijnbewaking_resterende_dagen_2_steekproef,varchar(20),einddatum_termijnbewaking_resterende_dagen_3_melding,varchar(20),einddatum_termijnbewaking_resterende_dagen_4_vaststelling,varchar(20),einddatum_termijnbewaking_resterende_dagen_correcties,varchar(200),einddatum_termijnbewaking_resterende_dagen_correcties_fb,varchar(200),einddatum_termijnbewaking_resterende_dagen_overige,varchar(200),einddatum_termijnbewaking_resterende_weken_1_verlening,varchar(20),einddatum_termijnbewaking_resterende_weken_2_steekproef,varchar(20),einddatum_termijnbewaking_resterende_weken_3_melding,varchar(20),einddatum_termijnbewaking_resterende_weken_4_vaststelling,varchar(20),einddatum_termijnbewaking_resterende_weken_correcties,varchar(200),einddatum_termijnbewaking_resterende_weken_correcties_fb,varchar(200),einddatum_termijnbewaking_resterende_weken_overige,varchar(200),functioneel_beheer,varchar(26),functioneel_beheer_groep,varchar(19),gebruiker_1,varchar(27),gebruiker_2,varchar(27),gebruiker_3,varchar(27),gebruiker_4,varchar(27),gebruiker_5,varchar(27),gebruiker_6,varchar(27),gebruiker_7,varchar(27),gebruiker_8,varchar(27),gebruiker_9,varchar(27),gebruiker_10,varchar(27),gebruiker_11,varchar(27),gebruiker_12,varchar(27),gebruiker_13,varchar(27),gebruiker_14,varchar(27),gebruiker_15,varchar(27),gebruiker_16,varchar(27),gebruiker_17,varchar(27),gebruiker_18,varchar(27),gebruiker_19,varchar(27),gebruiker_20,varchar(27),gebruiker_21,varchar(27),gebruiker_22,varchar(27),gebruiker_23,varchar(27),gebruiker_24,varchar(27),gebruiker_25,varchar(27),gebruiker_26,varchar(27),gebruiker_27,varchar(17),gebruiker_28,varchar(17),gebruiker_29,varchar(17),gebruiker_30,varchar(17),gebruiker_31,varchar(12),gebruikersrol_1,varchar(17),gebruikersrol_2,varchar(17),gebruikersrol_3,varchar(17),gebruikersrol_4,varchar(17),gebruikersrol_5,varchar(17),gebruikersrol_6,varchar(17),gebruikersrol_7,varchar(17),gebruikersrol_8,varchar(17),gebruikersrol_9,varchar(17),gebruikersrol_10,varchar(17),gebruikersrol_11,varchar(17),gebruikersrol_12,varchar(17),gebruikersrol_13,varchar(17),gebruikersrol_14,varchar(17),gebruikersrol_15,varchar(17),gebruikersrol_16,varchar(11),gebruikersrol_17,varchar(17),gebruikersrol_18,varchar(8),gebruikersrol_19,varchar(8),gebruikersrol_20,varchar(8),gebruikersrol_21,varchar(8),gebruikersrol_22,varchar(8),gebruikersrol_23,varchar(8),gebruikersrol_24,varchar(8),gebruikersrol_25,varchar(8),gebruikersrol_26,varchar(8),gebruikersrol_27,varchar(17),gebruikersrol_28,varchar(17),gebruikersrol_29,varchar(17),gebruikersrol_30,varchar(17),gebruikersrol_31,varchar(11),gegenereerd_veld_handmatig_ingevuld,varchar(3),gemachtigde,varchar(200),gemachtigde_id,varchar(200),huidig_definitief_besluit,varchar(26),opschorting_1,uint16,opschorting_2,uint16,opschorting_3,uint8,opschorting_4,uint8,opschorting_fase_1,varchar(15),opschorting_fase_2,varchar(15),opschorting_fase_3,varchar(15),opschorting_fase_4,varchar(12),organisatie_id,varchar(24),organisatie_naam,varchar(186),parquet_schema_name,varchar(11),parquet_type,varchar(12),periodiciteit_activiteiten,varchar(18),portefeuillehouder_monitoring,varchar(22),portefeuillehouder_vaststelling,varchar(28),portefeuillehouder_verlening,varchar(102),project_assistent,varchar(65),project_assistent_groep,varchar(19),regeling_id,varchar(24),regelingnaam,varchar(184),regelingnummer,uint8,rvo_dossiernummer,uint32,saldo,varchar(13),sas-conversiedossier,varchar(2),sas-dossiernummer,varchar(14),sas-regeling,varchar(107),sharepoint_nummer,varchar(12),startdatum_activiteiten,varchar(10),startdatum_termijnbewaking_1_verlening,varchar(10),startdatum_termijnbewaking_2_steekproef,varchar(10),startdatum_termijnbewaking_3_melding,varchar(10),startdatum_termijnbewaking_4_vaststelling,varchar(10),startdatum_termijnbewaking_correcties,varchar(200),startdatum_termijnbewaking_correcties_fb,varchar(200),startdatum_termijnbewaking_overige,varchar(200),status_termijnbewaking_1_verlening,varchar(26),status_termijnbewaking_2_steekproef,varchar(26),status_termijnbewaking_3_melding,varchar(26),status_termijnbewaking_4_vaststelling,varchar(26),status_termijnbewaking_correcties,varchar(200),status_termijnbewaking_correcties_fb,varchar(200),status_termijnbewaking_overige,varchar(200),statuskleur_termijnbewaking_actieve_hoofdfase,varchar(6),stemlijst_besluit,varchar(200),stemlijst_resultaat,varchar(200),subsidietype,varchar(18),team_subgroep,varchar(19),termijnbewaking_verdaagd_1_verlening,varchar(3),termijnbewaking_verdaagd_2_steekproef,varchar(3),termijnbewaking_verdaagd_3_melding,varchar(3),termijnbewaking_verdaagd_4_vaststelling,varchar(3),termijnbewaking_verdaagd_correcties,varchar(200),termijnbewaking_verdaagd_correcties_fb,varchar(200),termijnbewaking_verdaagd_overige,varchar(200),titel_aanvraag,varchar(246),vastgesteld_bedrag,varchar(12),vaststeller,varchar(47),vaststeller_groep,varchar(19),vergadering_besluit,varchar(200),vergadering_dossier_nummer,varchar(200),verleend_bedrag_of_bedrag_na_herziening_tussentijds,varchar(13),verlener,varchar(64),verlener_-_groep,varchar(40),vrijval,varchar(200)
    -> AttributeRemover
Note: Parquet velden verwijderen
AttributeRemover
    REMOVE_ATTRS = parquet_schema_name,parquet_type
    -> StringReplacer_verwijder_tekens

Bookmark: Aanpassing: aangevraagd_bedrag & verleend_bedrag_of_bedrag_na_herziening_tussentijds & vastgesteld_bedrag
Note: euroteken en spatie
StringReplacer_verwijder_tekens
    CASE = NO
    FIND_TEXT = [^0-9,]
    NO_MATCH = _FME_NO_OP_
    REGEXP = YES
    SRC_ATTRS = aangevraagd_bedrag,verleend_bedrag_of_bedrag_na_herziening_tussentijds,vastgesteld_bedrag
    TEST_STRING = Enter a string to test here...
    -> StringReplacer_Omzetten_komma
Note: komma omzetten naar punt
StringReplacer_Omzetten_komma
    CASE = NO
    FIND_TEXT = ,
    NO_MATCH = _FME_NO_OP_
    REGEXP = NO
    REPLACE_TEXT = .
    SRC_ATTRS = aangevraagd_bedrag,verleend_bedrag_of_bedrag_na_herziening_tussentijds,vastgesteld_bedrag
    -> AttributeManager
Note: Data type aanpassen
AttributeManager
    -> AttributeCreator_3
AttributeCreator_3
    ATTR_TABLE = SET_TO Privacy (varchar(200)) = $(_meta_privacy)
    -> DateTimeConverter_2

Bookmark: Datumvelden
DateTimeConverter_2
    DATETIME_ATTR = aanvraagdatum
    IN_FORMAT = %d-%m-%Y %T
    OUT_FORMAT = %Y-%m-%d %H:%M:%S
    PASSTHROUGH = YES
    REPAIR_INPUT = YES
    TEST_INPUT = 08-04-2025 20:34:55
    -> DateTimeConverter
DateTimeConverter
    DATETIME_ATTR = einddatum_termijnbewaking einddatum_taak einddatum_activiteiten
    IN_FORMAT = %d-%m-%Y$
    OUT_FORMAT = %Y-%m-%d
    PASSTHROUGH = YES
    REPAIR_INPUT = YES
    -> AttributeManager_2
AttributeManager_2
    -> aanvragen_v1 (writer MSSQL_AZURE_4)

Bookmark: Wegschrijven
aanvragen_v1 (writer MSSQL_AZURE_4)
    attributes: Privacy varchar(200), aangevraagd_bedrag bigint, vastgesteld_bedrag bigint, verleend_bedrag_of_bedrag_na_herziening_tussentijds bigint, aan_zet varchar(179), aangevraagd_via varchar(12), aanvraag_id varchar(24), aanvraagdatum datetime, aanvraagdatum_jaar integer, aanvraagdatum_maand tinyint, aanvraagdatum_weeknummer tinyint, aanvraagnummer varchar(9),PrimaryKey, aanvraagwijze_particulier_/_organisatie varchar(11), aanvrager_id varchar(24), aanvrager_naam varchar(14), actiestatus_medewerkers varchar(14), actieve__actie_11 varchar(79), actieve_actie_1 varchar(79), actieve_actie_2 varchar(79), actieve_actie_3 varchar(79), actieve_actie_4 varchar(79), actieve_actie_5 varchar(79), actieve_actie_6 varchar(60), actieve_actie_7 varchar(79), actieve_actie_8 varchar(60), actieve_actie_9 varchar(79), actieve_actie_10 varchar(60), actieve_actie_12 varchar(79), actieve_actie_13 varchar(60), actieve_actie_14 varchar(60),
      actieve_actie_15 varchar(60), actieve_actie_16 varchar(32), actieve_actie_17 varchar(34), actieve_actie_18 varchar(16), actieve_actie_19 varchar(17), actieve_actie_20 varchar(26), actieve_actie_21 varchar(14), actieve_actie_22 varchar(14), actieve_actie_23 varchar(33), actieve_actie_24 varchar(14), actieve_actie_25 varchar(33), actieve_actie_26 varchar(33), actieve_actie_27 varchar(50), actieve_actie_28 varchar(50), actieve_actie_29 varchar(50), actieve_actie_30 varchar(50), actieve_actie_31 varchar(24), actuele_actieve_hoofdfase varchar(15), actuele_actieve_subfase varchar(21), actuele_status varchar(29), afdeling_hoofdgroep varchar(12), besluit_genomen_1_verlening varchar(3), besluit_genomen_2_steekproef varchar(3), besluit_genomen_3_melding varchar(3), besluit_genomen_4_vaststelling varchar(3), besluit_genomen_correcties varchar(3), besluit_genomen_correcties_fb varchar(3), besluit_genomen_overige varchar(3), besluitvorming varchar(19), betaald varchar(13),
      boekjaar varchar(24), datum_besluit_1_verlening varchar(10), datum_besluit_2_steekproef varchar(10), datum_besluit_3_melding varchar(10), datum_besluit_4_vaststelling varchar(10), datum_besluit_correcties varchar(200), datum_besluit_correcties_fb varchar(200), datum_besluit_jaar_1_verlening integer, datum_besluit_jaar_2_steekproef integer, datum_besluit_jaar_3_melding integer, datum_besluit_jaar_4_vaststelling integer, datum_besluit_jaar_correcties varchar(200), datum_besluit_jaar_correcties_fb varchar(200), datum_besluit_jaar_overige varchar(200), datum_besluit_maand_1_verlening tinyint, datum_besluit_maand_2_steekproef tinyint, datum_besluit_maand_3_melding tinyint, datum_besluit_maand_4_vaststelling tinyint, datum_besluit_maand_correcties varchar(200), datum_besluit_maand_correcties_fb varchar(200), datum_besluit_maand_overige varchar(200), datum_besluit_overige varchar(200), datum_besluit_weeknummer_1_verlening tinyint, datum_besluit_weeknummer_2_steekproef tinyint, datum_besluit_weeknummer_3_melding tinyint, datum_besluit_weeknummer_4_vaststelling tinyint, datum_besluit_weeknummer_correcties varchar(200), datum_besluit_weeknummer_correcties_fb varchar(200), datum_besluit_weeknummer_overige varchar(200), deadline_hoofdfase varchar(10),
      documentnummer_besluit_1_verlening varchar(13), documentnummer_besluit_2_steekproef varchar(13), documentnummer_besluit_3_melding varchar(13), documentnummer_besluit_4_vaststelling varchar(13), documentnummer_besluit_correcties varchar(200), documentnummer_besluit_correcties_fb varchar(200), documentnummer_besluit_overige varchar(200), doorlooptijd:_912_juridisch_advies tinyint, doorlooptijd:_913_inhoudelijk_advies tinyint, doorlooptijd:_declaratie_indienen integer, doorlooptijd:_eindverantwoording_automatisch_opvragen tinyint, doorlooptijd:_iban_wijzigen tinyint, doorlooptijd:_intrekken_aanvraag tinyint, doorlooptijd:_melding_doorgeven integer, doorlooptijd:_tussenverantwoording_automatisch_opvragen tinyint, doorlooptijd:_vraag_stellen_/_bericht_sturen tinyint, einddatum_activiteiten datetime, einddatum_taak datetime, einddatum_termijnbewaking datetime, einddatum_termijnbewaking_1_verlening varchar(10), einddatum_termijnbewaking_2_steekproef varchar(10), einddatum_termijnbewaking_3_melding varchar(10), einddatum_termijnbewaking_4_vaststelling varchar(10), einddatum_termijnbewaking_correcties varchar(200), einddatum_termijnbewaking_correcties_fb varchar(200), einddatum_termijnbewaking_overige varchar(200), einddatum_termijnbewaking_resterende_dagen_1_verlening varchar(20), einddatum_termijnbewaking_resterende_dagen_2_steekproef varchar(20), einddatum_termijnbewaking_resterende_dagen_3_melding varchar(20), einddatum_termijnbewaking_resterende_dagen_4_vaststelling varchar(20),
      einddatum_termijnbewaking_resterende_dagen_correcties varchar(200), einddatum_termijnbewaking_resterende_dagen_correcties_fb varchar(200), einddatum_termijnbewaking_resterende_dagen_overige varchar(200), einddatum_termijnbewaking_resterende_weken_1_verlening varchar(20), einddatum_termijnbewaking_resterende_weken_2_steekproef varchar(20), einddatum_termijnbewaking_resterende_weken_3_melding varchar(20), einddatum_termijnbewaking_resterende_weken_4_vaststelling varchar(20), einddatum_termijnbewaking_resterende_weken_correcties varchar(200), einddatum_termijnbewaking_resterende_weken_correcties_fb varchar(200), einddatum_termijnbewaking_resterende_weken_overige varchar(200), functioneel_beheer varchar(26), functioneel_beheer_groep varchar(19), gebruiker_1 varchar(27), gebruiker_2 varchar(27), gebruiker_3 varchar(27), gebruiker_4 varchar(27), gebruiker_5 varchar(27), gebruiker_6 varchar(27), gebruiker_7 varchar(27), gebruiker_8 varchar(27), gebruiker_9 varchar(27), gebruiker_10 varchar(27), gebruiker_11 varchar(27), gebruiker_12 varchar(27), gebruiker_13 varchar(27), gebruiker_14 varchar(27), gebruiker_15 varchar(27), gebruiker_16 varchar(27), gebruiker_17 varchar(27), gebruiker_18 varchar(27),
      gebruiker_19 varchar(27), gebruiker_20 varchar(27), gebruiker_21 varchar(27), gebruiker_22 varchar(27), gebruiker_23 varchar(27), gebruiker_24 varchar(27), gebruiker_25 varchar(27), gebruiker_26 varchar(27), gebruiker_27 varchar(17), gebruiker_28 varchar(17), gebruiker_29 varchar(17), gebruiker_30 varchar(17), gebruiker_31 varchar(12), gebruikersrol_1 varchar(17), gebruikersrol_2 varchar(17), gebruikersrol_3 varchar(17), gebruikersrol_4 varchar(17), gebruikersrol_5 varchar(17), gebruikersrol_6 varchar(17), gebruikersrol_7 varchar(17), gebruikersrol_8 varchar(17), gebruikersrol_9 varchar(17), gebruikersrol_10 varchar(17), gebruikersrol_11 varchar(17), gebruikersrol_12 varchar(17), gebruikersrol_13 varchar(17), gebruikersrol_14 varchar(17), gebruikersrol_15 varchar(17), gebruikersrol_16 varchar(11), gebruikersrol_17 varchar(17),
      gebruikersrol_18 varchar(8), gebruikersrol_19 varchar(8), gebruikersrol_20 varchar(8), gebruikersrol_21 varchar(8), gebruikersrol_22 varchar(8), gebruikersrol_23 varchar(8), gebruikersrol_24 varchar(8), gebruikersrol_25 varchar(8), gebruikersrol_26 varchar(8), gebruikersrol_27 varchar(17), gebruikersrol_28 varchar(17), gebruikersrol_29 varchar(17), gebruikersrol_30 varchar(17), gebruikersrol_31 varchar(11), gegenereerd_veld_handmatig_ingevuld varchar(3), gemachtigde varchar(200), gemachtigde_id varchar(200), huidig_definitief_besluit varchar(26), opschorting_1 integer, opschorting_2 integer, opschorting_3 tinyint, opschorting_4 tinyint, opschorting_fase_1 varchar(15), opschorting_fase_2 varchar(15), opschorting_fase_3 varchar(15), opschorting_fase_4 varchar(12), organisatie_id varchar(24), organisatie_naam varchar(186), periodiciteit_activiteiten varchar(18), portefeuillehouder_monitoring varchar(22),
      portefeuillehouder_vaststelling varchar(28), portefeuillehouder_verlening varchar(102), project_assistent varchar(65), project_assistent_groep varchar(19), regeling_id varchar(24), regelingnaam varchar(184), regelingnummer tinyint, rvo_dossiernummer bigint, saldo varchar(13), sas-conversiedossier varchar(2), sas-dossiernummer varchar(14), sas-regeling varchar(107), sharepoint_nummer varchar(12), startdatum_activiteiten varchar(10), startdatum_termijnbewaking_1_verlening varchar(10), startdatum_termijnbewaking_2_steekproef varchar(10), startdatum_termijnbewaking_3_melding varchar(10), startdatum_termijnbewaking_4_vaststelling varchar(10), startdatum_termijnbewaking_correcties varchar(200), startdatum_termijnbewaking_correcties_fb varchar(200), startdatum_termijnbewaking_overige varchar(200), status_termijnbewaking_1_verlening varchar(26), status_termijnbewaking_2_steekproef varchar(26), status_termijnbewaking_3_melding varchar(26), status_termijnbewaking_4_vaststelling varchar(26), status_termijnbewaking_correcties varchar(200), status_termijnbewaking_correcties_fb varchar(200), status_termijnbewaking_overige varchar(200), statuskleur_termijnbewaking_actieve_hoofdfase varchar(6), stemlijst_besluit varchar(200),
      stemlijst_resultaat varchar(200), subsidietype varchar(18), team_subgroep varchar(19), termijnbewaking_verdaagd_1_verlening varchar(3), termijnbewaking_verdaagd_2_steekproef varchar(3), termijnbewaking_verdaagd_3_melding varchar(3), termijnbewaking_verdaagd_4_vaststelling varchar(3), termijnbewaking_verdaagd_correcties varchar(200), termijnbewaking_verdaagd_correcties_fb varchar(200), termijnbewaking_verdaagd_overige varchar(200), titel_aanvraag varchar(246), vaststeller varchar(47), vaststeller_groep varchar(19), vergadering_besluit varchar(200), vergadering_dossier_nummer varchar(200), verlener varchar(64), verlener_-_groep varchar(40), vrijval varchar(200)

Bookmark: Workflowformulieren
Creator4
    GEOMTYPE = Geometry Object
    NUM = 1
    CREATED -> AttributeCreator
AttributeCreator
    ATTR_TABLE:
      SET_TO folder (varchar(200)) = $(FOLDER_NAME_IN)/
      SET_TO container (varchar(200)) = $(CONTAINER_IN)
    -> AzureBlobStorageConnector4
AzureBlobStorageConnector4
    CREDENTIAL_SOURCE = WEBCONN
    OPERATION_TYPE = List
    PARAMETER_SETUP = _FME_AZURE_CONTAINER]@Value(container)]_FME_FILES]@Value(folder)]_FME_INCLUDE_SUBFOLDERS]No]_FME_ATTRIBUTES_TO_ADD]"_url _full_path _name _created"]FME_CONTROLLER_QUERY_FILE]]FME_CONTROLLER_CHOICE]List
    _FME_AZURE_CONNECTION = Blob
    -> Sampler
Sampler
    MODE = ORIGINAL
    RATE = 1
    SAMPLE_TYPE_MULTIPLIER = 0
    SAMPLE_MODE = No
    SAMPLE_TYPE_LONG = Last N Features
    SAMPLED -> FeatureReader [INITIATOR]
FeatureReader
    ATTR_ACCUM_MODE = Only Use Result
    COMBINE_GEOM = Use Result
    DATASET = @Value(_url)
    FORMAT = PARQUET
    INITIATOR_FIRST_OUTPUT = default
    ORDER_RESULTS = No
    OUTPUT_FEATURES_DISPLAY = Data Features
    PARQUET_PARQUET_EXPOSE_FORMAT_ATTRS = fme_feature_type,string
    PARQUET_SUPPORT_ANNOTATED_LISTS = yes
    PARQUET_SUPPORT_GEOMETRY = yes
    PARQUET_SUPPORT_LISTS = yes
    PARQUET_SUPPORT_LOCAL_TIME = yes
    <OTHER> -> AttributeExposer
AttributeExposer
    ATTR_TABLE = aanvraagnummer,varchar(9),antwoord,varchar(13760),datum,varchar(10),formulier,varchar(56),hoofdfase,varchar(15),regeling,varchar(184),sharepoint_nummer,varchar(12),vergadering_dossier_nummer,varchar(200),vraag,varchar(706)
    -> UniqueIdentifierGenerator

Bookmark: Opschonen en verrijken
UniqueIdentifierGenerator
    UUID_ATTR = uniek_id
    UUID_FORMAT = ULID
    -> DateTimeConverter_3
Note: Naar welk format moet dit worden weggeschreven?
DateTimeConverter_3
    DATETIME_ATTR = datum
    IN_FORMAT = %d-%m-%Y$
    OUT_FORMAT = %Y-%m-%d
    PASSTHROUGH = YES
    REPAIR_INPUT = YES
    -> AttributeManager_3
AttributeManager_3
    -> workflowformulieren_v1 (writer MSSQL_AZURE_2)

Bookmark: Wegschrijven
workflowformulieren_v1 (writer MSSQL_AZURE_2)
    attributes: aanvraagnummer varchar(9), antwoord varchar(13760), datum date, formulier varchar(56), hoofdfase varchar(15), regeling varchar(184), sharepoint_nummer varchar(12), vergadering_dossier_nummer varchar(200), vraag varchar(706), uniek_id char(26),PrimaryKey
